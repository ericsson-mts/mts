-- **************************************************************
--
-- Information Element Definitions
--
-- **************************************************************

S1AP-IEs { 
itu-t (0) identified-organization (4) etsi (0) mobileDomain (0) 
eps-Access (21) modules (3) s1ap (1) version1 (1) s1ap-IEs (2) }

DEFINITIONS AUTOMATIC TAGS ::= 

BEGIN

IMPORTS
	id-E-RABInformationListItem,
	id-E-RABItem,
	id-Bearers-SubjectToStatusTransfer-Item,
	maxNrOfCSGs,
	maxNrOfE-RABs,
	maxNrOfErrors,
	maxnoofBPLMNs,
	maxnoofPLMNsPerMME,
	maxnoofTACs,
	maxnoofEPLMNs,
	maxnoofEPLMNsPlusOne,
	maxnoofForbLACs,
	maxnoofForbTACs,
	maxnoofCells,
	maxnoofCellID,
	maxnoofEmergencyAreaID,
	maxnoofTAIforWarning,
	maxnoofCellinTAI,
	maxnoofCellinEAI,
	maxnoofeNBX2TLAs,
	maxnoofRATs,
	maxnoofGroupIDs,
	maxnoofMMECs,
    maxProtocolExtensions,
    maxNrOfIndividualS1ConnectionsToReset,
    maxnoofTAIs,
    maxProtocolIEs
FROM S1AP-Constants

    IE
FROM S1AP-PDU

	Criticality,
	ProcedureCode,
	ProtocolIE-ID,
    ProtocolExtensionID,
	TriggeringMessage
FROM S1AP-CommonDataTypes;

-- FH modif
--IE-Extensions ::= SEQUENCE (SIZE (1..maxProtocolExtensions)) OF IE
IE-Extensions ::= SEQUENCE SIZE (1..maxProtocolExtensions) OF IE
-- A


AllocationAndRetentionPriority ::= SEQUENCE {
	priorityLevel				PriorityLevel,
	pre-emptionCapability		Pre-emptionCapability,
	pre-emptionVulnerability	Pre-emptionVulnerability,
--	iE-Extensions				ProtocolExtensionContainer { {AllocationAndRetentionPriority-ExtIEs} } OPTIONAL,
    iE-Extensions               IE-Extensions OPTIONAL
  -- FH modif
	--...
}

-- FH modif
--/*
--AllocationAndRetentionPriority-ExtIEs S1AP-PROTOCOL-EXTENSION ::= {
--	...
--}*/


-- B

-- FH modif
--Bearers-SubjectToStatusTransfer-List ::= SEQUENCE (SIZE(1.. maxNrOfE-RABs)) OF IE
Bearers-SubjectToStatusTransfer-List ::= SEQUENCE SIZE (1.. maxNrOfE-RABs) OF IE

Bearers-SubjectToStatusTransfer-Item ::= SEQUENCE {
	e-RAB-ID								E-RAB-ID,
	uL-COUNTvalue								COUNTvalue,
	dL-COUNTvalue								COUNTvalue,
	receiveStatusofULPDCPSDUs					ReceiveStatusofULPDCPSDUs			OPTIONAL,
    iE-Extensions                               IE-Extensions OPTIONAL  
    -- FH modif
    --...
}

-- FH modif
--/*
--Bearers-SubjectToStatusTransfer-ItemExtIEs S1AP-PROTOCOL-EXTENSION ::= {
--	...
--}*/

BitRate	::= INTEGER (0..10000000000) 

-- FH modif
--BPLMNs ::= SEQUENCE (SIZE(1.. maxnoofBPLMNs)) OF PLMNidentity
BPLMNs ::= SEQUENCE SIZE (1.. maxnoofBPLMNs) OF PLMNidentity

BroadcastCompletedAreaList ::= CHOICE {
	cellID-Broadcast				CellID-Broadcast,
	tAI-Broadcast					TAI-Broadcast,
	emergencyAreaID-Broadcast		EmergencyAreaID-Broadcast
  -- FH modif
	--...
}


-- C

Cause ::= CHOICE {
	radioNetwork		CauseRadioNetwork,
	transport			CauseTransport,
	nas					CauseNas,
	protocol			CauseProtocol,
	misc				CauseMisc
	-- FH modif
	--...
}

CauseMisc ::= ENUMERATED {
	control-processing-overload(0),
	not-enough-user-plane-processing-resources(1),
	hardware-failure(2),
	om-intervention(3),
	unspecified(4),
	unknown-PLMN(5)
  -- FH modif
	--...
}

CauseProtocol ::= ENUMERATED {
	transfer-syntax-error(0),
	abstract-syntax-error-reject(1),
	abstract-syntax-error-ignore-and-notify(2),
	message-not-compatible-with-receiver-state(3),
	semantic-error(4),
	abstract-syntax-error-falsely-constructed-message(5),
	unspecified(6)
	-- FH modif
	--...
}

CauseRadioNetwork ::= ENUMERATED {
	unspecified(0),
	tx2relocoverall-expiry(1),
	successful-handover(2),
	release-due-to-eutran-generated-reason(3),
	handover-cancelled(4),	
	partial-handover(5),	
	ho-failure-in-target-EPC-eNB-or-target-system(6),
	ho-target-not-allowed(7),
	tS1relocoverall-expiry(8),
	tS1relocprep-expiry(9),
	cell-not-available(10),
	unknown-targetID(11),
	no-radio-resources-available-in-target-cell(12),
	unknown-mme-ue-s1ap-id(13),
	unknown-enb-ue-s1ap-id(14),
	unknown-pair-ue-s1ap-id(15),
	handover-desirable-for-radio-reason(16),
	time-critical-handover(17),
	resource-optimisation-handover(18),
	reduce-load-in-serving-cell(19),
	user-inactivity(20),
	radio-connection-with-ue-lost(21),
	load-balancing-tau-required(22),
	cs-fallback-triggered(23),
	ue-not-available-for-ps-service(24),
	radio-resources-not-available(25),
	failure-in-radio-interface-procedure(26),
	invalid-qos-combination(27),
	interrat-redirection(28),
	interaction-with-other-procedure(29),
	unknown-E-RAB-ID(30),
	multiple-E-RAB-ID-instances(31),
	encryption-and-or-integrity-protection-algorithms-not-supported(32),
	s1-intra-system-handover-triggered(33),
	s1-inter-system-handover-triggered(34),
	x2-handover-triggered(35),
  -- FH modif
	--...,
	redirection-towards-1xRTT(254),
	not-supported-QCI-value(255)

}

CauseTransport ::= ENUMERATED {
	transport-resource-unavailable(0),
	unspecified(1)
	-- FH modif
	--...
}

CauseNas ::= ENUMERATED {
	normal-release(0),
	authentication-failure(1),
	detach(2),
	unspecified(3)
	-- FH modif
	--...
}

CellIdentity			::= BIT STRING (SIZE (28))
                                                                               
-- FH modif                                                                              
--CellID-Broadcast ::= SEQUENCE (SIZE(1..maxnoofCellID)) OF CellID-Broadcast-Item
CellID-Broadcast ::= SEQUENCE SIZE (1..maxnoofCellID) OF CellID-Broadcast-Item

CellID-Broadcast-Item ::= SEQUENCE {
	eCGI				EUTRAN-CGI,
--	iE-Extensions		ProtocolExtensionContainer { {CellID-Broadcast-Item-ExtIEs} } OPTIONAL,
  iE-Extensions               IE-Extensions OPTIONAL
	-- FH modif
	--...
}

--FH modif
--/*
--CellID-Broadcast-Item-ExtIEs S1AP-PROTOCOL-EXTENSION ::= {
--	...
--}*/


Cdma2000PDU	::= OCTET STRING

Cdma2000RATType ::= ENUMERATED {
	hRPD(0),
	onexRTT(1)
	-- FH modif
	--...
}

Cdma2000SectorID ::= OCTET STRING

Cdma2000HOStatus ::= ENUMERATED {
	hOSuccess(0),
	hOFailure(1)
	-- FH modif
	--...
}

Cdma2000HORequiredIndication ::= ENUMERATED {
	true(0)
	-- FH modif
	--...
}

Cdma2000OneXSRVCCInfo ::= SEQUENCE {
	cdma2000OneXMEID			Cdma2000OneXMEID,
	cdma2000OneXMSI				Cdma2000OneXMSI,
	cdma2000OneXPilot			Cdma2000OneXPilot,
--	iE-Extensions				ProtocolExtensionContainer { {Cdma2000OneXSRVCCInfo-ExtIEs} } OPTIONAL,
  iE-Extensions             IE-Extensions OPTIONAL
	-- FH modif
	--...
}

-- FH modif
--/*
--Cdma2000OneXSRVCCInfo-ExtIEs S1AP-PROTOCOL-EXTENSION ::= {
--	...
--}*/

Cdma2000OneXMEID ::= OCTET STRING

Cdma2000OneXMSI ::= OCTET STRING

Cdma2000OneXPilot ::= OCTET STRING

Cdma2000OneXRAND ::= OCTET STRING


Cell-Size ::= ENUMERATED 
{
    verysmall(0), 
    small(1), 
    medium(2), 
    large(3) 
    -- FH modif
    --...
}

CellType ::= SEQUENCE {
	cell-Size				Cell-Size,
--	iE-Extensions			ProtocolExtensionContainer { { CellType-ExtIEs}}	OPTIONAL,
    iE-Extensions               IE-Extensions OPTIONAL
    -- FH modif
    --...
}

-- FH modif
--/*
--CellType-ExtIEs S1AP-PROTOCOL-EXTENSION ::= {
--	...
--}*/

CGI ::= SEQUENCE {
	pLMNidentity				PLMNidentity,
	lAC				LAC,
	cI				CI,
	rAC				RAC						OPTIONAL,
--	iE-Extensions	ProtocolExtensionContainer { {CGI-ExtIEs} } OPTIONAL,
    iE-Extensions               IE-Extensions OPTIONAL
	  -- FH modif
	  --...
}

-- FH modif
--/*
--CGI-ExtIEs S1AP-PROTOCOL-EXTENSION ::= {
--	...
--}*/

CI					::= OCTET STRING (SIZE (2))

CNDomain ::= ENUMERATED {
	ps(1), 
	cs(2) 
}

CSFallbackIndicator ::= ENUMERATED { 
	cs-fallback-required(0),
	-- FH modif
	--...,
	cs-fallback-high-priority(255) 
}

CSG-Id		::= BIT STRING (SIZE (27))

--FH modif
--CSG-IdList ::= SEQUENCE (SIZE (1..maxNrOfCSGs)) OF CSG-IdList-Item
CSG-IdList ::= SEQUENCE SIZE (1..maxNrOfCSGs) OF CSG-IdList-Item

CSG-IdList-Item ::= SEQUENCE {
	cSG-Id			CSG-Id,
--	iE-Extensions	ProtocolExtensionContainer { {CSG-IdList-Item-ExtIEs} } OPTIONAL,
    iE-Extensions               IE-Extensions OPTIONAL
	  -- FH modif                                         
    --...
}

-- FH modif
--/*
--CSG-IdList-Item-ExtIEs S1AP-PROTOCOL-EXTENSION ::= {
--	...
--}*/

COUNTvalue ::= SEQUENCE {
	pDCP-SN			PDCP-SN,
	hFN				HFN,
--	iE-Extensions	ProtocolExtensionContainer { {COUNTvalue-ExtIEs} } OPTIONAL,
    iE-Extensions               IE-Extensions OPTIONAL
	  -- FH modif
    --...
}

-- FH modif
--/*
--COUNTvalue-ExtIEs S1AP-PROTOCOL-EXTENSION ::= {
--	...
--}*/

CriticalityDiagnostics ::= SEQUENCE {
	procedureCode					ProcedureCode					OPTIONAL,
	triggeringMessage				TriggeringMessage				OPTIONAL,
	procedureCriticality			Criticality						OPTIONAL,
	iEsCriticalityDiagnostics		CriticalityDiagnostics-IE-List 	OPTIONAL,
--	iE-Extensions					ProtocolExtensionContainer {{CriticalityDiagnostics-ExtIEs}} OPTIONAL,
    iE-Extensions                   IE-Extensions OPTIONAL
	  -- FH modif
    --...
}

--CriticalityDiagnostics-ExtIEs S1AP-PROTOCOL-EXTENSION ::= {
--	...
--}

-- FH modif
--CriticalityDiagnostics-IE-List ::= SEQUENCE (SIZE (1..maxNrOfErrors)) OF CriticalityDiagnostics-IE-Item
CriticalityDiagnostics-IE-List ::= SEQUENCE SIZE (1..maxNrOfErrors) OF CriticalityDiagnostics-IE-Item

CriticalityDiagnostics-IE-Item ::= 	SEQUENCE {
	iECriticality			Criticality,
	iE-ID					ProtocolIE-ID,
	typeOfError 			TypeOfError,
--	iE-Extensions			ProtocolExtensionContainer {{CriticalityDiagnostics-IE-Item-ExtIEs}} OPTIONAL,
    iE-Extensions           IE-Extensions OPTIONAL
    -- FH modif
    --...
}

--CriticalityDiagnostics-IE-Item-ExtIEs S1AP-PROTOCOL-EXTENSION ::= {
--	...
--}


-- D

DataCodingScheme ::= BIT STRING (SIZE (8))

DL-Forwarding ::= ENUMERATED {
	dL-Forwarding-proposed(0)
	-- FH modif
	--...
}

Direct-Forwarding-Path-Availability ::= ENUMERATED {
	directPathAvailable(0)
	-- FH modif
	--...
}

-- E

-- FH modif
--E-RABToBeModifiedListBearerModReq ::= SEQUENCE (SIZE(1.. maxNrOfE-RABs)) OF IE
E-RABToBeModifiedListBearerModReq ::= SEQUENCE SIZE(1.. maxNrOfE-RABs) OF IE

E-RABToBeModifiedItemBearerModReq ::= SEQUENCE {
	e-RAB-ID						E-RAB-ID,
	e-RABLevelQoSParameters			E-RABLevelQoSParameters,
	nAS-PDU							NAS-PDU,
--	iE-Extensions					ProtocolExtensionContainer { {E-RABToBeModifyItemBearerModReqExtIEs} } OPTIONAL,
	iE-Extensions           IE-Extensions OPTIONAL
	-- FH modif
	--...
}

-- FH modif
--E-RABReleaseListBearerRelComp ::= SEQUENCE (SIZE(1.. maxNrOfE-RABs)) OF IE
E-RABReleaseListBearerRelComp ::= SEQUENCE SIZE(1.. maxNrOfE-RABs) OF IE

E-RABReleaseItemBearerRelComp ::= SEQUENCE {
	e-RAB-ID					E-RAB-ID,
--	iE-Extensions					ProtocolExtensionContainer { {E-RABReleaseItemBearerRelCompExtIEs} } OPTIONAL,
	iE-Extensions           IE-Extensions OPTIONAL
	-- FH modif
	--...
}

-- FH modif
--E-RABDataForwardingList ::= SEQUENCE (SIZE (0..maxNrOfE-RABs)) OF IE
E-RABDataForwardingList ::= SEQUENCE SIZE (0..maxNrOfE-RABs) OF IE

E-RABDataForwardingItem ::= SEQUENCE {
	e-RAB-ID							E-RAB-ID,
	dL-transportLayerAddress			TransportLayerAddress 													OPTIONAL,
	dL-gTP-TEID							GTP-TEID 																OPTIONAL,
	uL-TransportLayerAddress			TransportLayerAddress													OPTIONAL,
	uL-GTP-TEID							GTP-TEID																OPTIONAL,
--	iE-Extensions						ProtocolExtensionContainer { { E-RABDataForwardingItem-ExtIEs} }	OPTIONAL,
	iE-Extensions           IE-Extensions OPTIONAL
	-- FH modif
	--...
}

-- FH modif
--E-RABToBeSetupListCtxtSUReq ::= SEQUENCE (SIZE(1..maxNrOfE-RABs)) OF IE
E-RABToBeSetupListCtxtSUReq ::= SEQUENCE SIZE (1..maxNrOfE-RABs) OF IE

E-RABToBeSetupItemCtxtSUReq ::= SEQUENCE {
	e-RAB-ID					E-RAB-ID,
	e-RABlevelQoSParameters					E-RABLevelQoSParameters,		
	transportLayerAddress 			TransportLayerAddress,
	gTP-TEID			GTP-TEID,
	nAS-PDU				NAS-PDU		OPTIONAL,
--	iE-Extensions					ProtocolExtensionContainer { {E-RABToBeSetupItemCtxtSUReqExtIEs} } OPTIONAL,
	iE-Extensions           IE-Extensions OPTIONAL
	-- FH modif
	--...
}

-- FH modif
--E-RABSetupListBearerSURes ::= SEQUENCE (SIZE(1.. maxNrOfE-RABs)) OF IE
E-RABSetupListBearerSURes ::= SEQUENCE SIZE (1.. maxNrOfE-RABs) OF IE

E-RABSetupItemBearerSURes ::= SEQUENCE {
	e-RAB-ID					E-RAB-ID,
	transportLayerAddress		TransportLayerAddress,
	gTP-TEID					GTP-TEID,
--	iE-Extensions				ProtocolExtensionContainer { {E-RABSetupItemBearerSUResExtIEs} } OPTIONAL,
	iE-Extensions           IE-Extensions OPTIONAL
	-- FH modif
	--...
}

-- FH modif
--E-RABFailedtoSetupListHOReqAck ::= SEQUENCE (SIZE (0..maxNrOfE-RABs)) OF IE
E-RABFailedtoSetupListHOReqAck ::= SEQUENCE SIZE (0..maxNrOfE-RABs) OF IE

E-RABFailedToSetupItemHOReqAck ::= SEQUENCE {
	e-RAB-ID						E-RAB-ID,
	cause				Cause,
--	iE-Extensions					ProtocolExtensionContainer { { E-RABFailedToSetupItemHOReqAckExtIEs} }			OPTIONAL,
	iE-Extensions           IE-Extensions OPTIONAL
	-- FH modif
	--...
}

-- FH modif
--E-RABToBeSetupListBearerSUReq ::= SEQUENCE (SIZE(1.. maxNrOfE-RABs)) OF IE
E-RABToBeSetupListBearerSUReq ::= SEQUENCE SIZE(1.. maxNrOfE-RABs) OF IE

E-RABToBeSetupItemBearerSUReq ::= SEQUENCE {
	e-RAB-ID						E-RAB-ID,
	e-RABlevelQoSParameters			E-RABLevelQoSParameters,
	transportLayerAddress 			TransportLayerAddress,
	gTP-TEID						GTP-TEID,
	nAS-PDU							NAS-PDU,
--	iE-Extensions					ProtocolExtensionContainer { {E-RABToBeSetupItemBearerSUReqExtIEs} } OPTIONAL,
	iE-Extensions           IE-Extensions OPTIONAL
	-- FH modif
	--...
}

-- FH modif
--E-RABAdmittedList ::= SEQUENCE (SIZE (0..maxNrOfE-RABs)) OF IE
E-RABAdmittedList ::= SEQUENCE SIZE (0..maxNrOfE-RABs) OF IE

E-RABAdmittedItem ::= SEQUENCE {
	e-RAB-ID						E-RAB-ID,
	transportLayerAddress			TransportLayerAddress,
	gTP-TEID						GTP-TEID,
	dL-transportLayerAddress		TransportLayerAddress	OPTIONAL,
	dL-gTP-TEID						GTP-TEID				OPTIONAL,
	uL-TransportLayerAddress		TransportLayerAddress	OPTIONAL,
	uL-GTP-TEID						GTP-TEID				OPTIONAL,
--	iE-Extensions					ProtocolExtensionContainer { {E-RABAdmittedItem-ExtIEs} }	OPTIONAL,
	iE-Extensions           IE-Extensions OPTIONAL
	-- FH modif
	--...
}

-- FH modif
--E-RABToBeSwitchedDLList ::= SEQUENCE (SIZE (0..maxNrOfE-RABs)) OF IE
E-RABToBeSwitchedDLList ::= SEQUENCE SIZE (0..maxNrOfE-RABs) OF IE

E-RABToBeSwitchedDLItem ::= SEQUENCE {
	e-RAB-ID						E-RAB-ID,
	transportLayerAddress				TransportLayerAddress,
	gTP-TEID					GTP-TEID,
--	iE-Extensions					ProtocolExtensionContainer { { E-RABToBeSwitchedDLItem-ExtIEs} }			OPTIONAL,
	iE-Extensions           IE-Extensions OPTIONAL
	-- FH modif
	--...
}

-- FH modif
--E-RABToBeSwitchedULList ::= SEQUENCE (SIZE (0..maxNrOfE-RABs)) OF IE
E-RABToBeSwitchedULList ::= SEQUENCE SIZE (0..maxNrOfE-RABs) OF IE

E-RABToBeSwitchedULItem ::= SEQUENCE {
	e-RAB-ID							E-RAB-ID,
	transportLayerAddress				TransportLayerAddress,
	gTP-TEID							GTP-TEID,
--	iE-Extensions						ProtocolExtensionContainer { { E-RABToBeSwitchedULItem-ExtIEs} }			OPTIONAL,
	iE-Extensions           IE-Extensions OPTIONAL
	-- FH modif
	--...
}

-- FH modif
--E-RABModifyListBearerModRes ::= SEQUENCE (SIZE(1.. maxNrOfE-RABs)) OF IE
E-RABModifyListBearerModRes ::= SEQUENCE SIZE(1.. maxNrOfE-RABs) OF IE

E-RABModifyItemBearerModRes ::= SEQUENCE {
	e-RAB-ID					E-RAB-ID,
    iE-Extensions           IE-Extensions OPTIONAL
    -- FH modif
    --...
}

-- FH modif
--E-RABSetupListCtxtSURes ::= SEQUENCE (SIZE(1.. maxNrOfE-RABs)) OF IE
E-RABSetupListCtxtSURes ::= SEQUENCE SIZE(1.. maxNrOfE-RABs) OF IE

E-RABSetupItemCtxtSURes ::= SEQUENCE {
	e-RAB-ID					E-RAB-ID,
	transportLayerAddress 			TransportLayerAddress,
	gTP-TEID			GTP-TEID,
--	iE-Extensions					ProtocolExtensionContainer { {E-RABSetupItemCtxtSUResExtIEs} } OPTIONAL,
	iE-Extensions           IE-Extensions OPTIONAL
	-- FH modif
	--...
}

-- FH modif
--E-RABToBeSetupListHOReq ::= SEQUENCE (SIZE(1.. maxNrOfE-RABs)) OF IE
E-RABToBeSetupListHOReq ::= SEQUENCE SIZE(1.. maxNrOfE-RABs) OF IE

E-RABToBeSetupItemHOReq ::= SEQUENCE {
	e-RAB-ID							E-RAB-ID,
	transportLayerAddress				TransportLayerAddress,
	gTP-TEID							GTP-TEID,
	e-RABlevelQosParameters				E-RABLevelQoSParameters,
--	iE-Extensions						ProtocolExtensionContainer { {E-RABToBeSetupItemHOReq-ExtIEs} }			OPTIONAL,
	iE-Extensions           IE-Extensions OPTIONAL
	-- FH modif
	--...
}

--FH modif
--ECGIList ::= SEQUENCE (SIZE(1..maxnoofCellID)) OF EUTRAN-CGI
ECGIList ::= SEQUENCE SIZE(1..maxnoofCellID) OF EUTRAN-CGI

-- FH modif
--EmergencyAreaIDList ::= SEQUENCE (SIZE(1..maxnoofEmergencyAreaID)) OF EmergencyAreaID
EmergencyAreaIDList ::= SEQUENCE SIZE(1..maxnoofEmergencyAreaID) OF EmergencyAreaID

EmergencyAreaID ::= OCTET STRING (SIZE (3))

-- FH modif
--EmergencyAreaID-Broadcast ::= SEQUENCE (SIZE(1..maxnoofEmergencyAreaID)) OF EmergencyAreaID-Broadcast-Item
EmergencyAreaID-Broadcast ::= SEQUENCE SIZE(1..maxnoofEmergencyAreaID) OF EmergencyAreaID-Broadcast-Item

EmergencyAreaID-Broadcast-Item ::= SEQUENCE {
	emergencyAreaID			EmergencyAreaID,
	completedCellinEAI		CompletedCellinEAI,
--	iE-Extensions			ProtocolExtensionContainer { {EmergencyAreaID-Broadcast-Item-ExtIEs} } OPTIONAL,
    iE-Extensions           IE-Extensions OPTIONAL
	  -- FH modif
    --...
}

--EmergencyAreaID-Broadcast-Item-ExtIEs S1AP-PROTOCOL-EXTENSION ::= {
--	...
--}

-- FH modif
--CompletedCellinEAI ::= SEQUENCE (SIZE(1..maxnoofCellinEAI)) OF CompletedCellinEAI-Item
CompletedCellinEAI ::= SEQUENCE SIZE(1..maxnoofCellinEAI) OF CompletedCellinEAI-Item

CompletedCellinEAI-Item ::= SEQUENCE {
	eCGI					EUTRAN-CGI,
--	iE-Extensions			ProtocolExtensionContainer { {CompletedCellinEAI-Item-ExtIEs} } OPTIONAL,
    iE-Extensions           IE-Extensions OPTIONAL
	  -- FH modif
    --...
}

-- FH modif
--/*
--CompletedCellinEAI-Item-ExtIEs S1AP-PROTOCOL-EXTENSION ::= {
--	...
--}*/

ENB-ID ::= CHOICE {
	macroENB-ID			BIT STRING (SIZE(20)),
	homeENB-ID			BIT STRING (SIZE(28))
	-- FH modif
	--...
}

GERAN-Cell-ID ::= SEQUENCE {
	lAI				LAI,
    rAC				RAC, 
	cI				CI,
--	iE-Extensions			ProtocolExtensionContainer { { GERAN-Cell-ID-ExtIEs} } OPTIONAL,
    iE-Extensions           IE-Extensions OPTIONAL
	  -- FH modif
    --...
}

--GERAN-Cell-ID-ExtIEs S1AP-PROTOCOL-EXTENSION ::= {
--	...
--}

Global-ENB-ID ::= SEQUENCE {
	pLMNidentity			PLMNidentity,
	eNB-ID					ENB-ID,
	--iE-Extensions			ProtocolExtensionContainer { {GlobalENB-ID-ExtIEs} } OPTIONAL,
	iE-Extensions           IE-Extensions OPTIONAL
	-- FH modif
	--...
}

--GlobalENB-ID-ExtIEs S1AP-PROTOCOL-EXTENSION ::= {
--	...
--}


ENB-StatusTransfer-TransparentContainer		::= SEQUENCE {
	bearers-SubjectToStatusTransfer-List		Bearers-SubjectToStatusTransfer-List,
    iE-Extensions           IE-Extensions OPTIONAL
	  -- FH modif
    --...
}

ENB-UE-S1AP-ID				::= INTEGER (0..16777215)

ENBname ::= PrintableString (SIZE (1..150,...))

-- FH modif
--ENBX2TLAs ::= SEQUENCE (SIZE(1.. maxnoofeNBX2TLAs)) OF TransportLayerAddress
ENBX2TLAs ::= SEQUENCE SIZE(1.. maxnoofeNBX2TLAs) OF TransportLayerAddress

EncryptionAlgorithms ::= BIT STRING (SIZE (16,...))

-- FH modif
--EPLMNs ::= SEQUENCE (SIZE(1..maxnoofEPLMNs)) OF PLMNidentity
EPLMNs ::= SEQUENCE SIZE(1..maxnoofEPLMNs) OF PLMNidentity

EventType	::= ENUMERATED {
	direct(0),
	change-of-serve-cell(1),
	stop-change-of-serve-cell(2)
	-- FH modif
	--...
}

E-RAB-ID		::= INTEGER (0..15, ...)
                                          
--E-RABInformationList	::= SEQUENCE (SIZE (1.. maxNrOfE-RABs)) OF ProtocolIE-SingleContainer { { E-RABInformationListIEs } }
-- FH modif
--E-RABInformationList	::= SEQUENCE (SIZE (1.. maxNrOfE-RABs)) OF IE
E-RABInformationList	::= SEQUENCE SIZE (1.. maxNrOfE-RABs) OF IE

--E-RABInformationListIEs S1AP-PROTOCOL-IES ::= {
--	{ ID id-E-RABInformationListItem			CRITICALITY ignore	TYPE E-RABInformationListItem			PRESENCE mandatory	},
--	...
--}

E-RABInformationListItem ::= SEQUENCE {
	e-RAB-ID					E-RAB-ID,
	dL-Forwarding					DL-Forwarding		OPTIONAL,
--	iE-Extensions					ProtocolExtensionContainer { {E-RABInformationListItem-ExtIEs} }			OPTIONAL,
    iE-Extensions               IE-Extensions OPTIONAL
	  -- FH modif
    --...
}

-- FH modif
--/*
--E-RABInformationListItem-ExtIEs S1AP-PROTOCOL-EXTENSION ::= {
--	...
--}*/

--E-RABList ::= SEQUENCE (SIZE(1.. maxNrOfE-RABs)) OF ProtocolIE-SingleContainer { {E-RABItemIEs} }
-- FH modif
--E-RABList ::= SEQUENCE (SIZE(1.. maxNrOfE-RABs)) OF ANY
E-RABList ::= SEQUENCE SIZE(1.. maxNrOfE-RABs) OF ANY

--E-RABItemIEs 	S1AP-PROTOCOL-IES ::= {
--	{ ID id-E-RABItem	 CRITICALITY ignore 	TYPE E-RABItem 	PRESENCE mandatory },
--	...
--}

E-RABItem ::= SEQUENCE {
	e-RAB-ID				E-RAB-ID,
	cause						Cause,
--	iE-Extensions				ProtocolExtensionContainer { {E-RABItem-ExtIEs} } OPTIONAL,
    iE-Extensions               IE-Extensions OPTIONAL
    -- FH modif
    --...
}

-- FH modif
--/*
--E-RABItem-ExtIEs S1AP-PROTOCOL-EXTENSION ::= {
--	...
--}*/




E-RABLevelQoSParameters ::= SEQUENCE {
	qCI			QCI,
	allocationRetentionPriority			AllocationAndRetentionPriority,
	gbrQosInformation					GBR-QosInformation			OPTIONAL,
--	iE-Extensions						ProtocolExtensionContainer { {E-RABQoSParameters-ExtIEs} } OPTIONAL,
    iE-Extensions               IE-Extensions OPTIONAL
	  -- FH modif  
    --...
}

-- FH modif
--/*
--E-RABQoSParameters-ExtIEs S1AP-PROTOCOL-EXTENSION ::= {
--	...
--}*/


EUTRAN-CGI ::= SEQUENCE {
	pLMNidentity			PLMNidentity,
	cell-ID					CellIdentity,
--	iE-Extensions			ProtocolExtensionContainer { {EUTRAN-CGI-ExtIEs} } OPTIONAL,
    iE-Extensions           IE-Extensions OPTIONAL
	  -- FH modif
	  --...
}

-- FH modif
--/*
--EUTRAN-CGI-ExtIEs S1AP-PROTOCOL-EXTENSION ::= {
--	...
--}*/

ExtendedRNC-ID					::= INTEGER (4096..65535)

-- F

ForbiddenInterRATs ::= ENUMERATED {
	all(0),
	geran(1),
	utran(2),
	cdma2000(3)
	-- FH modif
	--...
}

-- FH modif
--ForbiddenTAs ::= SEQUENCE (SIZE(1.. maxnoofEPLMNsPlusOne)) OF ForbiddenTAs-Item
ForbiddenTAs ::= SEQUENCE SIZE(1.. maxnoofEPLMNsPlusOne) OF ForbiddenTAs-Item

ForbiddenTAs-Item ::= SEQUENCE {
	pLMN-Identity		PLMNidentity,
	forbiddenTACs		ForbiddenTACs,
--	iE-Extensions		ProtocolExtensionContainer { {ForbiddenTAs-Item-ExtIEs} } OPTIONAL,
    iE-Extensions       IE-Extensions OPTIONAL
	  -- FH modif
    --...
}

-- FH modif
--/*
--ForbiddenTAs-Item-ExtIEs S1AP-PROTOCOL-EXTENSION ::= {
--	...
--}*/

-- FH modif
--ForbiddenTACs ::= SEQUENCE (SIZE(1..maxnoofForbTACs)) OF TAC
ForbiddenTACs ::= SEQUENCE SIZE(1..maxnoofForbTACs) OF TAC

-- FH modif
--ForbiddenLAs ::= SEQUENCE (SIZE(1..maxnoofEPLMNsPlusOne)) OF ForbiddenLAs-Item
ForbiddenLAs ::= SEQUENCE SIZE(1..maxnoofEPLMNsPlusOne) OF ForbiddenLAs-Item

ForbiddenLAs-Item ::= SEQUENCE {
	pLMN-Identity		PLMNidentity,
	forbiddenLACs		ForbiddenLACs,
--	iE-Extensions		ProtocolExtensionContainer { {ForbiddenLAs-Item-ExtIEs} } OPTIONAL,
    iE-Extensions       IE-Extensions OPTIONAL
	  -- FH modif
	  --...
}

-- FH modif
--/*
--ForbiddenLAs-Item-ExtIEs S1AP-PROTOCOL-EXTENSION ::= {
--	...
--}*/

-- FH modif
--ForbiddenLACs ::= SEQUENCE (SIZE(1..maxnoofForbLACs)) OF LAC
ForbiddenLACs ::= SEQUENCE SIZE(1..maxnoofForbLACs) OF LAC

-- G

GBR-QosInformation ::= SEQUENCE {
	e-RAB-MaximumBitrateDL			BitRate,
	e-RAB-MaximumBitrateUL			BitRate,
	e-RAB-GuaranteedBitrateDL		BitRate,
	e-RAB-GuaranteedBitrateUL		BitRate,
--	iE-Extensions						ProtocolExtensionContainer { { GBR-QosInformation-ExtIEs} } OPTIONAL,
    iE-Extensions                   IE-Extensions OPTIONAL
	  -- FH modif
	  --...
}

-- FH modif
--/*
--GBR-QosInformation-ExtIEs S1AP-PROTOCOL-EXTENSION ::= {
--	...
--}*/


GTP-TEID					::= OCTET STRING (SIZE (4))

GUMMEI			::= SEQUENCE {
	pLMN-Identity		PLMNidentity,
	mME-Group-ID		MME-Group-ID,
	mME-Code			MME-Code,
--	iE-Extensions					ProtocolExtensionContainer { {GUMMEI-ExtIEs} } OPTIONAL,
    iE-Extensions       IE-Extensions OPTIONAL
	  -- FH modif
	  --...
}

-- FH modif
--/*
--GUMMEI-ExtIEs S1AP-PROTOCOL-EXTENSION ::= {
--	...
--}*/

-- H

HandoverRestrictionList ::= SEQUENCE {
	servingPLMN					PLMNidentity,
	equivalentPLMNs				EPLMNs					OPTIONAL,
	forbiddenTAs				ForbiddenTAs			OPTIONAL,
	forbiddenLAs				ForbiddenLAs			OPTIONAL,
	forbiddenInterRATs				ForbiddenInterRATs			OPTIONAL, 
--	iE-Extensions				ProtocolExtensionContainer { {HandoverRestrictionList-ExtIEs} }	OPTIONAL,
    iE-Extensions               IE-Extensions OPTIONAL
	  -- FH modif
	  --...
}

-- FH modif
--/*
--HandoverRestrictionList-ExtIEs S1AP-PROTOCOL-EXTENSION ::= {
--	...
--}*/

HandoverType ::= ENUMERATED {
	intralte(0),
	ltetoutran(1),
	ltetogeran(2),
	utrantolte(3),
	gerantolte(4)
	-- FH modif
	--...
}

HFN ::= INTEGER (0..1048575)

-- I

Inter-SystemInformationTransferType ::= CHOICE {
	rIMTransfer		RIMTransfer
	-- FH modif
	--...
}

IMSI	::=	OCTET STRING (SIZE (3..8))

IntegrityProtectionAlgorithms ::= BIT STRING (SIZE (16,...))

InterfacesToTrace ::= BIT STRING (SIZE (8))



-- J
-- K
-- L


LAC	::= OCTET STRING (SIZE (2))

LAI ::= SEQUENCE {
	pLMNidentity				PLMNidentity,
	lAC				LAC,
--	iE-Extensions			ProtocolExtensionContainer { {LAI-ExtIEs} } OPTIONAL,
    iE-Extensions IE-Extensions OPTIONAL
	  -- FH modif
	  --...
}

-- FH modif
--/*
--LAI-ExtIEs S1AP-PROTOCOL-EXTENSION ::= {
--	...
--}*/

LastVisitedCell-Item ::= CHOICE {
	e-UTRAN-Cell					LastVisitedEUTRANCellInformation,
	uTRAN-Cell						LastVisitedUTRANCellInformation,
	gERAN-Cell						LastVisitedGERANCellInformation
	-- FH modif
	--...
}
LastVisitedEUTRANCellInformation ::= SEQUENCE {
	global-Cell-ID					EUTRAN-CGI,
	cellType						CellType,
	time-UE-StayedInCell			Time-UE-StayedInCell,
--	iE-Extensions					ProtocolExtensionContainer { { LastVisitedEUTRANCellInformation-ExtIEs} } OPTIONAL,
    iE-Extensions                   IE-Extensions OPTIONAL
	  -- FH modif
	  --...
}

-- FH modif
--/*
--LastVisitedEUTRANCellInformation-ExtIEs S1AP-PROTOCOL-EXTENSION ::= {
--	...
--}*/

LastVisitedUTRANCellInformation	::= OCTET STRING

LastVisitedGERANCellInformation ::= CHOICE {
	undefined						NULL
	-- FH modif
	--...
}

L3-Information				::= OCTET STRING


-- M

MessageIdentifier	::= BIT STRING (SIZE (16))

MMEname ::= PrintableString (SIZE (1..150,...))

MME-Group-ID	::= OCTET STRING (SIZE (2))

MME-Code		::= OCTET STRING (SIZE (1))

MME-UE-S1AP-ID				::= INTEGER (0..4294967295)
M-TMSI			::= OCTET STRING (SIZE (4))

MSClassmark2	::= OCTET STRING
MSClassmark3	::= OCTET STRING

-- N

NAS-PDU ::=  OCTET STRING

NASSecurityParametersfromE-UTRAN ::= OCTET STRING

NASSecurityParameterstoE-UTRAN ::= OCTET STRING

NumberofBroadcastRequest ::= INTEGER (0..65535)

NumberOfBroadcasts ::= INTEGER (0..65535)

-- O
OldBSS-ToNewBSS-Information		::= OCTET STRING

OverloadAction ::= ENUMERATED {
    reject-non-emergency-mo-dt(0),
    reject-all-rrc-cr-signalling(1),
    permit-emergency-sessions-only(2)
	  -- FH modif
	  --...
}

OverloadResponse ::= CHOICE {
	overloadAction					OverloadAction
	-- FH modif
	--...
}


-- P

PagingDRX ::= ENUMERATED {
	v32(0),
	v64(1),
	v128(2),
	v256(3)
	-- FH modif
	--...
	}

PDCP-SN ::= INTEGER (0..4095) 

PLMNidentity 				::= TBCD-STRING
--PLMNidentity 				::= OCTET STRING (SIZE (3))

Pre-emptionCapability ::= ENUMERATED {
	shall-not-trigger-pre-emption(0),
	may-trigger-pre-emption(1)
}

Pre-emptionVulnerability ::= ENUMERATED {
	not-pre-emptable(0),
	pre-emptable(1)
}

PriorityLevel				::= INTEGER { spare (0), highest (1), lowest (14), no-priority (15) }
--FH modif 
-- (0..15)


-- Q

QCI						::= INTEGER (0..255)

-- R

ReceiveStatusofULPDCPSDUs ::= BIT STRING (SIZE(4096))

RelativeMMECapacity				::= INTEGER (0..255)

RAC					::= OCTET STRING (SIZE (1))


RequestType	::= SEQUENCE {
	eventType 				EventType,
	reportArea 				ReportArea,
--	iE-Extensions			ProtocolExtensionContainer { { RequestType-ExtIEs} }	OPTIONAL,
    iE-Extensions           IE-Extensions OPTIONAL
	  -- FH modif
	  --...
}

-- FH modif
--/*
--RequestType-ExtIEs S1AP-PROTOCOL-EXTENSION ::= {
--	...
--}*/

ResetType ::= CHOICE {
	s1-Interface		ResetAll,
	partOfS1-Interface		UE-associatedLogicalS1-ConnectionListRes
	-- FH modif
	--...
}

ResetAll ::= ENUMERATED {
	reset-all(0)
	-- FH modif
	--...
}

RIMTransfer ::= SEQUENCE {
	rIMInformation					RIMInformation,
	rIMRoutingAddress				RIMRoutingAddress		OPTIONAL,
--	iE-Extensions			ProtocolExtensionContainer { { RIMTransfer-ExtIEs} }			OPTIONAL,
    iE-Extensions           IE-Extensions OPTIONAL
  -- FH modif
	--...
}

-- FH modif
--/*
--RIMTransfer-ExtIEs S1AP-PROTOCOL-EXTENSION ::= {
--	...
--}*/

RIMInformation ::= OCTET STRING

RIMRoutingAddress ::= CHOICE {
	gERAN-Cell-ID			GERAN-Cell-ID
	-- FH modif
	--...
}

ReportArea ::= ENUMERATED {
	ecgi(0)
	-- FH modif
	--...
}

RepetitionPeriod ::= INTEGER (0..4095)


RNC-ID					::= INTEGER (0..4095)

RRC-Container	::= OCTET STRING

RRC-Establishment-Cause ::= ENUMERATED {
	emergency(0),
	highPriorityAccess(1),
	mt-Access(2),
	mo-Signalling(3),
	mo-Data(4)
	-- FH modif
	--...
}

-- S


SecurityKey	::= BIT STRING (SIZE(256))



SecurityContext ::= SEQUENCE {
	nextHopChainingCount		INTEGER (0..7),
	nextHopParameter			SecurityKey,
--	iE-Extensions				ProtocolExtensionContainer { { SecurityContext-ExtIEs} } OPTIONAL,
    iE-Extensions               IE-Extensions OPTIONAL
	  -- FH modif
	  --...
}

-- FH modif
--/*
--SecurityContext-ExtIEs S1AP-PROTOCOL-EXTENSION ::= {
--	...
--}*/

SerialNumber ::= BIT STRING (SIZE (16))

SONInformation ::= CHOICE{
	sONInformationRequest		SONInformationRequest,
	sONInformationReply			SONInformationReply
	-- FH modif
	--...
}

SONInformationRequest ::= ENUMERATED { 
	x2TNL-Configuration-Info(0)
	-- FH modif
	--...
}

SONInformationReply ::= SEQUENCE {
	x2TNLConfigurationInfo			X2TNLConfigurationInfo			OPTIONAL,
--	iE-Extensions					ProtocolExtensionContainer {{SONInformationReply-ExtIEs}} OPTIONAL,
    iE-Extensions-Container         IE-Extensions OPTIONAL
    -- FH modif
	  --...
}

-- FH modif
--/*
--SONInformationReply-ExtIEs S1AP-PROTOCOL-EXTENSION ::= {
--	...
--}*/


SONConfigurationTransfer ::= SEQUENCE {
	targeteNB-ID					TargeteNB-ID,
	sourceeNB-ID					SourceeNB-ID,
	sONInformation					SONInformation,
--	iE-Extensions			ProtocolExtensionContainer { { SONConfigurationTransfer-ExtIEs} }			OPTIONAL,
    iE-Extensions           IE-Extensions OPTIONAL
    -- FH modif
	  --...
}

-- FH modif
--/*
--SONConfigurationTransfer-ExtIEs S1AP-PROTOCOL-EXTENSION ::= {
--	...
--}*/



Source-ToTarget-TransparentContainer ::= OCTET STRING

SourceBSS-ToTargetBSS-TransparentContainer		::= OCTET STRING
SourceeNB-ID ::= SEQUENCE {
	global-ENB-ID	Global-ENB-ID,
	selected-TAI	TAI,
--	iE-Extensions	ProtocolExtensionContainer { {SourceeNB-ID-ExtIEs} } OPTIONAL
    iE-Extensions   IE-Extensions OPTIONAL
}

-- FH modif
--/*
--SourceeNB-ID-ExtIEs S1AP-PROTOCOL-EXTENSION ::= {
--	...
--}*/

SRVCCOperationPossible ::= ENUMERATED {
  possible(0)
	-- FH modif
	--...
}

SRVCCHOIndication ::= ENUMERATED {
	pSandCS(0),
	cSonly(1)
	-- FH modif
	--...
}

SourceeNB-ToTargeteNB-TransparentContainer		::= SEQUENCE {
	rRC-Container					RRC-Container,
	e-RABInformationList		E-RABInformationList		OPTIONAL,
	targetCell-ID					EUTRAN-CGI,
	subscriberProfileIDforRFP				SubscriberProfileIDforRFP		OPTIONAL,
	uE-HistoryInformation			UE-HistoryInformation,
--	iE-Extensions			ProtocolExtensionContainer { {SourceeNB-ToTargeteNB-TransparentContainer-ExtIEs} } OPTIONAL,
    iE-Extensions           IE-Extensions OPTIONAL
	  -- FH modif
	  --...
}

-- FH modif
--/*
--SourceeNB-ToTargeteNB-TransparentContainer-ExtIEs S1AP-PROTOCOL-EXTENSION ::= {
--	...
--}*/


SourceRNC-ToTargetRNC-TransparentContainer		::= OCTET STRING


-- FH modif 
--ServedGUMMEIs ::= SEQUENCE (SIZE (1.. maxnoofRATs)) OF ServedGUMMEIsItem
ServedGUMMEIs ::= SEQUENCE SIZE (1.. maxnoofRATs) OF ServedGUMMEIsItem

ServedGUMMEIsItem ::= SEQUENCE {
	servedPLMNs				ServedPLMNs,
	servedGroupIDs			ServedGroupIDs,
	servedMMECs				ServedMMECs,
--	iE-Extensions			ProtocolExtensionContainer { {ServedGUMMEIsItem-ExtIEs} }	OPTIONAL,
    iE-Extensions           IE-Extensions OPTIONAL
	  -- FH modif
	  --...
}

-- FH modif
--/*
--ServedGUMMEIsItem-ExtIEs S1AP-PROTOCOL-EXTENSION ::= {
--	...
--}*/

-- FH modif
--ServedGroupIDs ::= SEQUENCE (SIZE(1.. maxnoofGroupIDs)) OF MME-Group-ID
ServedGroupIDs ::= SEQUENCE SIZE (1.. maxnoofGroupIDs) OF MME-Group-ID
--ServedMMECs ::= SEQUENCE (SIZE(1.. maxnoofMMECs)) OF MME-Code
ServedMMECs ::= SEQUENCE SIZE (1.. maxnoofMMECs) OF MME-Code

-- FH modif
--ServedPLMNs ::= SEQUENCE (SIZE(1.. maxnoofPLMNsPerMME)) OF PLMNidentity
ServedPLMNs ::= SEQUENCE SIZE (1.. maxnoofPLMNsPerMME) OF PLMNidentity

SubscriberProfileIDforRFP ::= INTEGER (1..256) 

-- FH modif
--SupportedTAs ::= SEQUENCE (SIZE(1.. maxnoofTACs)) OF SupportedTAs-Item
SupportedTAs ::= SEQUENCE SIZE(1.. maxnoofTACs) OF SupportedTAs-Item

SupportedTAs-Item ::=	SEQUENCE  {
	tAC					TAC,
	broadcastPLMNs		BPLMNs,
--	iE-Extensions		ProtocolExtensionContainer { {SupportedTAs-Item-ExtIEs} } OPTIONAL,
    iE-Extensions       IE-Extensions OPTIONAL
	  -- FH modif
	  --...
}

-- FH modif
--/*
--SupportedTAs-Item-ExtIEs S1AP-PROTOCOL-EXTENSION ::= {
--	...
--}*/

S-TMSI ::= SEQUENCE {
	mMEC	MME-Code,
	m-TMSI	M-TMSI,
--	iE-Extensions		ProtocolExtensionContainer { {S-TMSI-ExtIEs} } OPTIONAL,
    iE-Extensions       IE-Extensions OPTIONAL
	  -- FH modif
	  --...
}

-- FH modif
--/*
--S-TMSI-ExtIEs S1AP-PROTOCOL-EXTENSION ::= {
--	...
--}*/

-- T

TAC ::= OCTET STRING (SIZE (2))

-- FH modif 
--TAIListforWarning ::= SEQUENCE (SIZE(1..maxnoofTAIforWarning)) OF TAI
TAIListforWarning ::= SEQUENCE SIZE (1..maxnoofTAIforWarning) OF TAI

-- FH modif
--TAIList ::= SEQUENCE (SIZE(1..maxnoofTAIs)) OF IE
TAIList ::= SEQUENCE SIZE (1..maxnoofTAIs) OF IE

TAIItem ::= SEQUENCE {
	tAI 							TAI,
--	iE-Extensions					ProtocolExtensionContainer { {TAIItemExtIEs} } OPTIONAL,
	iE-Extensions           IE-Extensions OPTIONAL
	-- FH modif
	--...
}

TAI ::= SEQUENCE {
	pLMNidentity			PLMNidentity,
	tAC						TAC,
--	iE-Extensions			ProtocolExtensionContainer { {TAI-ExtIEs} } OPTIONAL,
    iE-Extensions           IE-Extensions OPTIONAL
	  -- FH modif
	  --...
}

-- FH modif
--/*
--TAI-ExtIEs S1AP-PROTOCOL-EXTENSION ::= {
--	...
--}*/

-- FH modif
--TAI-Broadcast ::= SEQUENCE (SIZE(1..maxnoofTAIforWarning)) OF TAI-Broadcast-Item
TAI-Broadcast ::= SEQUENCE SIZE(1..maxnoofTAIforWarning) OF TAI-Broadcast-Item

TAI-Broadcast-Item ::= SEQUENCE {
	tAI					TAI,
	completedCellinTAI	CompletedCellinTAI,
--	iE-Extensions			ProtocolExtensionContainer { {TAI-Broadcast-Item-ExtIEs} } OPTIONAL,
    iE-Extensions           IE-Extensions OPTIONAL
	  -- FH modif
	  --...
}

-- FH modif
--/*
--TAI-Broadcast-Item-ExtIEs S1AP-PROTOCOL-EXTENSION ::= {
--	...
--}*/

-- FH modif
--CompletedCellinTAI ::= SEQUENCE (SIZE(1..maxnoofCellinTAI)) OF CompletedCellinTAI-Item
CompletedCellinTAI ::= SEQUENCE SIZE(1..maxnoofCellinTAI) OF CompletedCellinTAI-Item

CompletedCellinTAI-Item ::= SEQUENCE{
	eCGI				EUTRAN-CGI,
--	iE-Extensions		ProtocolExtensionContainer { {CompletedCellinTAI-Item-ExtIEs} } OPTIONAL,
    iE-Extensions       IE-Extensions OPTIONAL
	  -- FH modif
	  --...
}

-- FH modif
--/*
--CompletedCellinTAI-Item-ExtIEs S1AP-PROTOCOL-EXTENSION ::= {
--	...
--}*/

TBCD-STRING ::= OCTET STRING (SIZE (3))

TargetID ::= CHOICE {
	targeteNB-ID			TargeteNB-ID,
	targetRNC-ID			TargetRNC-ID,
	cGI				CGI
	-- FH modif
	--...
}

TargeteNB-ID ::= SEQUENCE {
	global-ENB-ID	Global-ENB-ID,
	selected-TAI	TAI,
--	iE-Extensions	ProtocolExtensionContainer { {TargeteNB-ID-ExtIEs} } OPTIONAL,
    iE-Extensions   IE-Extensions OPTIONAL
	  -- FH modif
	  --...
}

-- FH modif
--/*
--TargeteNB-ID-ExtIEs S1AP-PROTOCOL-EXTENSION ::= {
--	...
--}*/

TargetRNC-ID ::= SEQUENCE {
	lAI					LAI,
	rAC					RAC 		OPTIONAL,
	rNC-ID				RNC-ID,
	extendedRNC-ID		ExtendedRNC-ID		OPTIONAL,
--	iE-Extensions	ProtocolExtensionContainer { {TargetRNC-ID-ExtIEs} } OPTIONAL,
    iE-Extensions   IE-Extensions OPTIONAL
	  -- FH modif
	  --...
}

-- FH modif
--/*
--TargetRNC-ID-ExtIEs S1AP-PROTOCOL-EXTENSION ::= {
--	...
--}*/


TargeteNB-ToSourceeNB-TransparentContainer		::= SEQUENCE {
	rRC-Container					RRC-Container,
--	iE-Extensions			ProtocolExtensionContainer { {TargeteNB-ToSourceeNB-TransparentContainer-ExtIEs} } OPTIONAL,
    iE-Extensions           IE-Extensions OPTIONAL
	  -- FH modif
	  --...
}

-- FH modif
--/*
--TargeteNB-ToSourceeNB-TransparentContainer-ExtIEs S1AP-PROTOCOL-EXTENSION ::= {
--	...
--}*/

Target-ToSource-TransparentContainer ::= OCTET STRING
TargetRNC-ToSourceRNC-TransparentContainer		::= OCTET STRING
TargetBSS-ToSourceBSS-TransparentContainer		::= OCTET STRING

TimeToWait ::= ENUMERATED 
{
    v1s(0), 
    v2s(1), 
    v5s(2), 
    v10s(3), 
    v20s(4), 
    v60s(5) 
    -- FH modif
	  --...
}

Time-UE-StayedInCell ::= INTEGER (0..4095)

TransportLayerAddress		::= BIT STRING (SIZE(1..160, ...))

TraceActivation ::= SEQUENCE {
	e-UTRAN-Trace-ID					E-UTRAN-Trace-ID,
	interfacesToTrace			InterfacesToTrace,
traceDepth						TraceDepth,
traceCollectionEntityIPAddress	TransportLayerAddress,
--	iE-Extensions					ProtocolExtensionContainer { { TraceActivation-ExtIEs} }		OPTIONAL,
    iE-Extensions               IE-Extensions OPTIONAL
	  -- FH modif
	  --...
  
}

-- FH modif
--/*
--TraceActivation-ExtIEs S1AP-PROTOCOL-EXTENSION ::= {
--	...
--}*/

TraceDepth ::= ENUMERATED { 
	minimum(0),
	medium(1),
	maximum(2),
	minimumWithoutVendorSpecificExtension(3),
	mediumWithoutVendorSpecificExtension(4),
	maximumWithoutVendorSpecificExtension(5)
	-- FH modif
	--...
}

E-UTRAN-Trace-ID ::=  OCTET STRING (SIZE (8))

TypeOfError ::= ENUMERATED {
	not-understood(0),
	missing(1)
	-- FH modif
	--...
}

-- U

UEAggregateMaximumBitrate ::= SEQUENCE {
	uEaggregateMaximumBitRateDL				BitRate,
	uEaggregateMaximumBitRateUL				BitRate,
--	iE-Extensions							ProtocolExtensionContainer { {UEAggregate-MaximumBitrates-ExtIEs} } OPTIONAL,
    iE-Extensions                           IE-Extensions OPTIONAL
	  -- FH modif
	  --...
}

-- FH modif
--/*
--UEAggregate-MaximumBitrates-ExtIEs S1AP-PROTOCOL-EXTENSION ::= {
--	...
--}*/



UE-S1AP-IDs ::= CHOICE{
	uE-S1AP-ID-pair		UE-S1AP-ID-pair,
	mME-UE-S1AP-ID		MME-UE-S1AP-ID
	-- FH modif
	--...
}

UE-S1AP-ID-pair ::= SEQUENCE{
	mME-UE-S1AP-ID		MME-UE-S1AP-ID,
	eNB-UE-S1AP-ID		ENB-UE-S1AP-ID,
--	iE-Extensions		ProtocolExtensionContainer { {UE-S1AP-ID-pair-ExtIEs} } OPTIONAL,
    iE-Extensions       IE-Extensions OPTIONAL
	  -- FH modif
	  --...
}

-- FH modif
--/*
--UE-S1AP-ID-pair-ExtIEs S1AP-PROTOCOL-EXTENSION ::= {
--	...
--}*/


--WARNING: not the right IE definition...
-- FH modif
--UE-associatedLogicalS1-ConnectionListRes ::= SEQUENCE (SIZE(1.. maxNrOfIndividualS1ConnectionsToReset)) OF IE
UE-associatedLogicalS1-ConnectionListRes ::= SEQUENCE SIZE (1.. maxNrOfIndividualS1ConnectionsToReset) OF IE

-- FH modif
--UE-associatedLogicalS1-ConnectionListResAck ::= SEQUENCE (SIZE(1.. maxNrOfIndividualS1ConnectionsToReset)) OF IE
UE-associatedLogicalS1-ConnectionListResAck ::= SEQUENCE SIZE (1.. maxNrOfIndividualS1ConnectionsToReset) OF IE

UE-associatedLogicalS1-ConnectionItemRes ::= SET {
    ue-associatedLogicalS1-ConnectionItemRes-ies UE-associatedLogicalS1-ConnectionItem
    -- FH modif
	  --...
}

UE-associatedLogicalS1-ConnectionItem ::= SEQUENCE {
	mME-UE-S1AP-ID					MME-UE-S1AP-ID OPTIONAL,
	eNB-UE-S1AP-ID					ENB-UE-S1AP-ID OPTIONAL,
--	iE-Extensions					ProtocolExtensionContainer { { UE-associatedLogicalS1-ConnectionItemExtIEs} } OPTIONAL,
    iE-Extensions                   IE-Extensions OPTIONAL
	  -- FH modif
	  --...
}

-- FH modif
--/*
--UE-associatedLogicalS1-ConnectionItemExtIEs S1AP-PROTOCOL-EXTENSION ::= {
--	...
--}*/

UEIdentityIndexValue	::=	BIT STRING (SIZE (10))

-- FH modif
--UE-HistoryInformation ::= SEQUENCE (SIZE(1..maxnoofCells)) OF LastVisitedCell-Item
UE-HistoryInformation ::= SEQUENCE SIZE(1..maxnoofCells) OF LastVisitedCell-Item

UEPagingID ::= CHOICE {
	s-TMSI		S-TMSI,
	iMSI		IMSI
	-- FH modif
	--...
	}

UERadioCapability ::= OCTET STRING

UESecurityCapabilities ::= SEQUENCE {
	encryptionAlgorithms			EncryptionAlgorithms,
	integrityProtectionAlgorithms		IntegrityProtectionAlgorithms,
--	iE-Extensions				ProtocolExtensionContainer { { UESecurityCapabilities-ExtIEs} }		    OPTIONAL,
    iE-Extensions               IE-Extensions   OPTIONAL
  -- FH modif
	--...
}
-- FH modif
--/*
--UESecurityCapabilities-ExtIEs S1AP-PROTOCOL-EXTENSION ::= {
--	...
--}*/

-- V
-- W

WarningAreaList ::= CHOICE {
	cellIDList						ECGIList,
	trackingAreaListforWarning		TAIListforWarning,
	emergencyAreaIDList				EmergencyAreaIDList
	-- FH modif
	--...
}


WarningType ::= OCTET STRING (SIZE (2))

WarningSecurityInfo ::= OCTET STRING (SIZE (50))


WarningMessageContents ::= OCTET STRING (SIZE(1..9600))


-- X


X2TNLConfigurationInfo ::= SEQUENCE {
	eNBX2TransportLayerAddresses	ENBX2TLAs,
--	iE-Extensions					ProtocolExtensionContainer { { X2TNLConfigurationInfo-ExtIEs} } OPTIONAL,
    iE-Extensions                   IE-Extensions OPTIONAL
	  -- FH modif
	  --...
}

-- FH modif
--/*
--X2TNLConfigurationInfo-ExtIEs S1AP-PROTOCOL-EXTENSION ::= {
--	...
--}*/

-- Y
-- Z

END
