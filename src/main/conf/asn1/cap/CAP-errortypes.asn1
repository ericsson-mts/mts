-- $Id$
-- 3GPP TS 29.078 11.0.0 (2011-09)
-- 5.2	Error types

CAP-errortypes {itu-t(0) identified-organization(4) etsi(0) mobileDomain(0) umts-network(1) modules(3) cap-errortypes(51) version8(7)}

-- This module contains the type definitions for the CAP Error Types.
-- Where a parameter of type CHOICE is tagged with a specific tag value, the tag is automatically
-- replaced with an EXPLICIT tag of the same value.

DEFINITIONS IMPLICIT TAGS ::= BEGIN

IMPORTS

	ros-InformationObjects,
	datatypes,
	errorcodes
FROM CAP-object-identifiers {itu-t(0) identified-organization(4) etsi(0) mobileDomain(0)
umts-network(1) modules(3) cap-object-identifiers(100) version8(7)}

	ERROR
FROM Remote-Operations-Information-Objects ros-InformationObjects

	InvokeID,
	UnavailableNetworkResource
FROM CAP-datatypes datatypes

	errcode-canceled,
	errcode-cancelFailed,
	errcode-eTCFailed,
	errcode-improperCallerResponse,
	errcode-missingCustomerRecord,
	errcode-missingParameter,
	errcode-parameterOutOfRange,
	errcode-requestedInfoError,
	errcode-systemFailure,
	errcode-taskRefused,
	errcode-unavailableResource,
	errcode-unexpectedComponentSequence,
	errcode-unexpectedDataValue,
	errcode-unexpectedParameter,
	errcode-unknownLegID,
	errcode-unknownCSID,
	errcode-unknownPDPID
FROM CAP-errorcodes errorcodes

;

-- TYPE DEFINITION FOR CAP ERROR TYPES FOLLOWS

-- FHModif Remove ERROR{CODE PARAMETER}
--canceled ERROR1 ::= {
--	CODE	errcode-canceled
--	}
-- The operation has been canceled.

-- FHModif Remove ERROR{CODE PARAMETER}
--cancelFailed ERROR ::= {
--	PARAMETER	SEQUENCE {
--		problem					[0] ENUMERATED {
--			unknownOperation		(0),
--			tooLate					(1),
--			operationNotCancellable	(2)
--			},
--		operation				[1] InvokeID,
--		...
--		}
--	CODE	errcode-cancelFailed
--	}
-- The operation failed to be canceled.

-- FHModif Remove ERROR{CODE PARAMETER}
--eTCFailed ERROR ::= {
--	CODE	errcode-eTCFailed
--	}
-- The establish temporary connection failed.

-- FHModif Remove ERROR{CODE PARAMETER}
--improperCallerResponse ERROR ::= {
--	CODE	errcode-improperCallerResponse
--	}
-- The caller response was not as expected.

-- FHModif Remove ERROR{CODE PARAMETER}
--missingCustomerRecord ERROR ::= {
--	CODE	errcode-missingCustomerRecord
--	}
-- The Service Logic Program could not be found in the gsmSCF.

-- FHModif Remove ERROR{CODE PARAMETER}
--missingParameter ERROR ::= {
--	CODE	errcode-missingParameter
--	}
-- An expected optional parameter was not received.

-- FHModif Remove ERROR{CODE PARAMETER}
--parameterOutOfRange ERROR ::= {
--	CODE	errcode-parameterOutOfRange
--	}
-- The parameter was not as expected (e.g. missing or out of range).

-- FHModif Remove ERROR{CODE PARAMETER}
--requestedInfoError ERROR ::= {
--	PARAMETER	ENUMERATED {
--			unknownRequestedInfo		(1),
--			requestedInfoNotAvailable	(2)
--			}
--	CODE	errcode-requestedInfoError
--	}
-- The requested information cannot be found.

-- FHModif Remove ERROR{CODE PARAMETER}
--systemFailure ERROR ::= {
--	PARAMETER	UnavailableNetworkResource
--	CODE	errcode-systemFailure
--	}
-- The operation could not be completed due to a system failure at the serving physical entity.

-- FHModif Remove ERROR{CODE PARAMETER}
--taskRefused ERROR ::= {
--	PARAMETER	ENUMERATED {
--			generic						(0),
--			unobtainable				(1),
--			congestion					(2)
--			}
--	CODE	errcode-taskRefused
--	}
-- An entity normally capable of the task requested cannot or chooses not to perform the task at
-- this time. This includes error situations like congestion and unobtainable address as used in
-- e.g. the connect operation.)

-- FHModif Remove ERROR{CODE PARAMETER}
--unavailableResource ERROR ::= {
--	CODE	errcode-unavailableResource
--	}
-- A requested resource is not available at the serving entity.

-- FHModif Remove ERROR{CODE PARAMETER}
--unexpectedComponentSequence ERROR ::= {
--	CODE	errcode-unexpectedComponentSequence
--	}
-- An incorrect sequence of Components was received (e.g. 'DisconnectForwardConnection'
-- followed by 'PlayAnnouncement').

-- FHModif Remove ERROR{CODE PARAMETER}
--unexpectedDataValue ERROR ::= {
--	CODE	errcode-unexpectedDataValue
--	}
-- The data value was not as expected (e.g. route number expected but billing number received)

-- FHModif Remove ERROR{CODE PARAMETER}
--unexpectedParameter ERROR ::= {
--	CODE	errcode-unexpectedParameter
--	}
-- A parameter received was not expected.

-- FHModif Remove ERROR{CODE PARAMETER}
--unknownLegID ERROR ::= {
--	CODE	errcode-unknownLegID
--	}
-- Leg not known to the gsmSSF.

-- FHModif Remove ERROR{CODE PARAMETER}
--unknownCSID ERROR ::= {
--	CODE 	errcode-unknownCSID
--	}
-- Call Segment not known to the gsmSSF.

-- FHModif Remove ERROR{CODE PARAMETER}
--unknownPDPID ERROR ::= {
--	CODE	errcode-unknownPDPID
--	}
-- PDPID not known by the receiving entity.

END
