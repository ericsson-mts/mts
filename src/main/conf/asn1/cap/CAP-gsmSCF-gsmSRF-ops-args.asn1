-- $Id$
-- 3GPP TS 29.078 11.0.0 (2011-09)
-- 6.2	gsmSCF/gsmSRF interface
-- 6.2.1	gsmSCF/gsmSRF operations and arguments
CAP-gsmSCF-gsmSRF-ops-args {itu-t(0) identified-organization(4) etsi(0) mobileDomain(0)
umts-network(1) modules(3) cap-gsmSCF-gsmSRF-ops-args(103) version8(7)}

DEFINITIONS IMPLICIT TAGS ::= BEGIN

-- This module contains the operations and operation arguments used for the
-- gsmSRF - gsmSCF interface, for the control of circuit switched calls.

-- The table in subclause 2.1 lists the specifications that contain the modules
-- that are used by CAP.

IMPORTS

	OPERATION
FROM Remote-Operations-Information-Objects ros-InformationObjects

	opcode-playAnnouncement,
	opcode-promptAndCollectUserInformation,
	opcode-specializedResourceReport
FROM CAP-operationcodes operationcodes
-- The CAP Operation identifiers for CAP V4 in Rel-6 are the same as the CAP Operation
-- identifiers for CAP V4 in Rel-5.

	CallSegmentID, -- FHModif remove {}
	CollectedInfo,
	Digits, -- FHModif remove {}
	Extensions, -- FHModif remove {}
	InformationToSend -- FHModif remove {}
FROM CAP-datatypes datatypes
-- For Rel-6, the CAP-datatypes module is updated to version8(7); Object Identifier 'datatypes'
-- is also updated to version8(7). As a result, the present module uses Rel-6 data type definitions.

	canceled,
	improperCallerResponse,
	missingParameter,
	parameterOutOfRange,
	systemFailure,
	taskRefused,
	unavailableResource,
	unexpectedComponentSequence,
	unexpectedDataValue,
	unexpectedParameter,
	unknownCSID
FROM CAP-errortypes errortypes
-- For Rel-6, the CAP-errortypes module is updated to version8(7); Object Identifier
-- 'errortypes' is also updated to version8(7). As a result, the present module uses Rel-6
-- error type definitions.

	PARAMETERS-BOUND
FROM CAP-classes classes

	ros-InformationObjects,
	operationcodes,
	datatypes,
	errortypes,
	classes
FROM CAP-object-identifiers {itu-t(0) identified-organization(4) etsi(0) mobileDomain(0)
umts-network(1) modules(3) cap-object-identifiers(100) version8(7)}

;

-- FHModif Remove OPERATION {ARGUMENT RETURN ERRORS CODE}
--playAnnouncement {PARAMETERS-BOUND : bound} OPERATION ::= {
--	ARGUMENT		PlayAnnouncementArg {bound}
--	RETURN RESULT	FALSE
--	ERRORS			{canceled |
--					missingParameter |
--					parameterOutOfRange |
--					systemFailure |
--					taskRefused |
--					unexpectedComponentSequence |
--					unexpectedDataValue |
--					unexpectedParameter |
--					unavailableResource |
--					unknownCSID}
--	LINKED			{specializedResourceReport}
--	CODE			opcode-playAnnouncement}
-- Direction: gsmSCF -> gsmSRF, Timer: Tpa
-- This operation is to be used after Establish Temporary Connection (assist procedure
-- with a second gsmSSF) or a Connect to Resource (no assist) operation. It may be used
-- for inband interaction with a mobile station, or for interaction with an ISDN user.
-- In the former case, the gsmSRF is usually collocated with the gsmSSF for standard
-- tones (congestion tone...) or standard announcements.
-- In the latter case, the gsmSRF is always collocated with the gsmSSF in the switch.
-- Any error is returned to the gsmSCF. The timer associated with this operation must
-- be of a sufficient duration to allow its linked operation to be correctly correlated.

-- FHModif Remove {PARAMETER-BOUND : bound}
PlayAnnouncementArg ::= SEQUENCE {
	informationToSend					[0] InformationToSend, -- FHModif {bound}
	disconnectFromIPForbidden			[1] BOOLEAN DEFAULT TRUE,
	requestAnnouncementCompleteNotification	[2] BOOLEAN DEFAULT TRUE,
	extensions							[3] Extensions						OPTIONAL, -- FHModif {bound}
	callSegmentID						[5] CallSegmentID					OPTIONAL, -- FHModif {bound}
	requestAnnouncementStartedNotification	[51] BOOLEAN DEFAULT FALSE
  -- FHModif, ...
	}

-- FHModif Remove OPERATION {ARGUMENT RETURN ERRORS CODE}
--promptAndCollectUserInformation {PARAMETERS-BOUND : bound} OPERATION ::= {
--	ARGUMENT		PromptAndCollectUserInformationArg {bound}
--	RESULT			ReceivedInformationArg {bound}
--	ERRORS			{canceled |
--					improperCallerResponse |
--					missingParameter |
--					parameterOutOfRange |
--					systemFailure |
--					taskRefused |
--					unexpectedComponentSequence |
--					unavailableResource |
--					unexpectedDataValue |
--					unexpectedParameter |
--					unknownCSID}
--	LINKED			{specializedResourceReport}
--	CODE			opcode-promptAndCollectUserInformation}
-- Direction: gsmSCF -> gsmSRF, Timer: Tpc
-- This operation is used to interact with a user to collect information.

-- FHModif Remove {PARAMETER-BOUND : bound}
PromptAndCollectUserInformationArg ::= SEQUENCE {
	collectedInfo						[0] CollectedInfo,
	disconnectFromIPForbidden			[1] BOOLEAN	DEFAULT TRUE,
	informationToSend					[2] InformationToSend 				OPTIONAL, -- FHModif {bound}
	extensions							[3] Extensions 						OPTIONAL, -- FHModif {bound}
	callSegmentID						[4]	CallSegmentID 					OPTIONAL, -- FHModif {bound}
	requestAnnouncementStartedNotification [51] BOOLEAN DEFAULT FALSE
  -- FHModif, ...
	}

-- FHModif Remove {PARAMETER-BOUND : bound}
ReceivedInformationArg ::= CHOICE {
	digitsResponse						[0] Digits -- FHModif {bound}
	}

-- FHModif Remove OPERATION {ARGUMENT RETURN ERRORS CODE}
--specializedResourceReport OPERATION ::= {
--	ARGUMENT		SpecializedResourceReportArg
--	RETURN RESULT	FALSE
--	ALWAYS RESPONDS	FALSE
--	CODE			opcode-specializedResourceReport}
-- Direction: gsmSRF -> gsmSCF, Timer: Tsrr
-- This operation is used as the response to a PlayAnnouncement operation when the announcement
-- completed report indication is set.

SpecializedResourceReportArg ::= CHOICE {
	allAnnouncementsComplete			[50] NULL,
	firstAnnouncementStarted			[51] NULL
	}

END
