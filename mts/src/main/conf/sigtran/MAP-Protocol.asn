--          Expanded ASN1 Module 'MAP-Protocol'          
--SIEMENS ASN.1 Compiler       R5.70  (Production_5.70)    
--            Date: 2003-09-04 Time: 14:14:00            

MAP-Protocol{ 0 identified-organization (4) etsi (0) mobileDomain (0) gsm-Network (1) modules (3) map-Protocol (4) version5 (5) }

DEFINITIONS::=

BEGIN

-- ROS def's
-- Module Remote-Operations-Apdus (H.450.1:02/1998)
--Remote-Operations-Apdus {itu-t recommendation h 450 1 version1(0)
--  remote-operations-apdus(11)} DEFINITIONS AUTOMATIC TAGS ::=
--BEGIN

Component ::=	CHOICE {
				invoke				[1] IMPLICIT Invoke,
				returnResultLast	[2] IMPLICIT ReturnResult,
				returnError			[3] IMPLICIT ReturnError,
				reject				[4] IMPLICIT Reject
}

Invoke ::=		SEQUENCE {
				invokeID			InvokeIdType,
				linkedID			[0] IMPLICIT InvokeIdType OPTIONAL,
				opCode				Operation,
				invokeparameter	 	InvokeParameter OPTIONAL
}
InvokeParameter ::= Mo-forwardSM-Arg

 
-- ANY is filled by the single ASN.1 data type following the keyword PARAMETER or the keyword ARGUMENT
-- in the type definition of a particular operation.

ReturnResult ::=	SEQUENCE {
				invokeID				InvokeIdType,
				resultretres			SEQUENCE {
				opCode					Operation,
				returnparameter				ReturnResultParameter OPTIONAL
				} OPTIONAL
			}

ReturnResultParameter ::= ANY

-- ANY is filled by the single ASN.1 data type following the keyword RESULT in the type definition
-- of a particular operation.

ReturnError ::=	SEQUENCE {
				invokeID				InvokeIdType,
				errorCode				Error,
				parameter				ReturnErrorParameter  OPTIONAL }

ReturnErrorParameter ::= ANY
 
-- ANY is filled by the single ASN.1 data type following the keyword PARAMETER in the type definition
-- of a particular error.

Reject ::=		SEQUENCE {
				invokeIDRej CHOICE {
					derivable			InvokeIdType,
					not-derivable		NULL },
				problem CHOICE {
					generalProblem		[0] IMPLICIT GeneralProblem,
					invokeProblem		[1] IMPLICIT InvokeProblem,
					returnResultProblem	[2] IMPLICIT ReturnResultProblem,
					returnErrorProblem	[3] IMPLICIT ReturnErrorProblem } }

InvokeIdType ::=	INTEGER (-128..127)


Operation	::=	CHOICE {
							localValue OperationLocalvalue,
							globalValue OBJECT IDENTIFIER } 

OperationLocalvalue ::= INTEGER{
	updateLocation (2),
	cancelLocation (3),
	provideRoamingNumber (4),
	noteSubscriberDataModified (5),
	resumeCallHandling (6),
	insertSubscriberData (7),
	deleteSubscriberData (8),
	sendParameters (9),
	registerSS (10),
	eraseSS (11),
	activateSS (12),
	deactivateSS (13),
	interrogateSS (14),
	authenticationFailureReport (15),
	registerPassword (17),
	getPassword (18),
	processUnstructuredSS-Data (19),
	releaseResources (20),
	sendRoutingInfo (22),
	updateGprsLocation (23),
	sendRoutingInfoForGprs (24),
	failureReport (25),
	noteMsPresentForGprs (26),
	performHandover (28),
	sendEndSignal (29),
	performSubsequentHandover (30),
	provideSIWFSNumber (31),
	sIWFSSignallingModify (32),
	processAccessSignalling (33),
	forwardAccessSignalling (34),
	noteInternalHandover (35),
	reset (37),
	forwardCheckSS (38),
	prepareGroupCall (39),
	sendGroupCallEndSignal (40),
	processGroupCallSignalling (41),
	forwardGroupCallSignalling (42),
	checkIMEI (43),
	mt-forwardSM (44),
	sendRoutingInfoForSM (45),
	mo-forwardSM (46),
	reportSM-DeliveryStatus (47),
	noteSubscriberPresent (48),
	alertServiceCentreWithoutResult (49),
	activateTraceMode (50),
	deactivateTraceMode (51),
	traceSubscriberActivity (52),
	beginSubscriberActivity (54),
	sendIdentification (55),
	sendAuthenticationInfo (56),
	restoreData (57),
	sendIMSI (58),
	processUnstructuredSS-Request (59),
	unstructuredSS-Request (60),
	unstructuredSS-Notify (61),
	anyTimeSubscriptionInterrogation (62),
	informServiceCentre (63),
	alertServiceCentre (64),
	anyTimeModification (65),
	readyForSM (66),
	purgeMS (67),
	prepareHandover (68),
	prepareSubsequentHandover (69),
	provideSubscriberInfo (70),
	anyTimeInterrogation (71),
	ss-InvocationNotification (72),
	setReportingState (73),
	statusReport (74),
	remoteUserFree (75),
	registerCC-Entry (76),
	eraseCC-Entry (77),
	secureTransportClass1 (78),
	secureTransportClass2 (79),
	secureTransportClass3 (80),
	secureTransportClass4 (81),
	provideSubscriberLocation (83),
	sendRoutingInfoForLCS (85),
	subscriberLocationReport (86),
	ist-Alert (87),
	ist-Command (88),
	noteMM-Event (89)
		}

Error	::=	CHOICE {
			localValue LocalErrorcode,
			globalValue OBJECT IDENTIFIER } 

LocalErrorcode ::= INTEGER{
	systemFailure (34),
	dataMissing (35),
	unexpectedDataValue (36),
	facilityNotSupported (21),
	incompatibleTerminal (28),
	resourceLimitation (51),
	unknownSubscriber (1),
	numberChanged (44),
	unknownMSC (3),
	unidentifiedSubscriber (5),
	unknownEquipment (7),
	roamingNotAllowed (8),
	illegalSubscriber (9),
	illegalEquipment (12),
	bearerServiceNotProvisioned (10),
	teleserviceNotProvisioned (11),
	noHandoverNumberAvailable (25),
	subsequentHandoverFailure (26),
	targetCellOutsideGroupCallArea (42),
	tracingBufferFull (40),
	noRoamingNumberAvailable (39),
	absentSubscriber (27),
	busySubscriber (45),
	noSubscriberReply (46),
	callBarred (13),
	forwardingViolation (14),
	forwardingFailed (47),
	cug-Reject (15),
	or-NotAllowed (48),
	ati-NotAllowed (49),
	atsi-NotAllowed (60),
	atm-NotAllowed (61),
	informationNotAvailabl (62),
	illegalSS-Operation (16),
	ss-ErrorStatus (17),
	ss-NotAvailable (18),
	ss-SubscriptionViolatio (19),
	ss-Incompatibility (20),
	unknownAlphabe (71),
	ussd-Busy (72),
	pw-RegistrationFailur (37),
	negativePW-Check (38),
	numberOfPW-AttemptsViolation (43),
	shortTermDenial (29),
	longTermDenial (30),
	subscriberBusyForMT-SMS (31),
	sm-DeliveryFailure (32),
	messageWaitingListFull (33),
	absentSubscriberSM (6),
	noGroupCallNumberAvailable (50),
	unauthorizedRequestingNetwork (52),
	unauthorizedLCSClient (53),
	positionMethodFailure (54),
	unknownOrUnreachableLCSClient (58),
	mm-EventNotSupported (59),
	secureTransportError (4)
	}

-- PROBLEMS

GeneralProblem		::=	INTEGER {		unrecognizedComponent (0),
								mistypedComponent (1),
								badlyStructuredComponent (2) }

InvokeProblem		::=	INTEGER {		duplicateInvokeID (0),
								unrecognizedOperation (1),
								mistypedParameter (2),
								resourceLimitation (3),
								initiatingRelease (4),
								unrecognizedLinkedID (5),
								linkedResponseUnexpected (6),
								unexpectedLinkedOperation (7) }

ReturnResultProblem	::=	INTEGER {		unrecognizedInvokeID (0),
								returnResultUnexpected (1),
								mistypedParameter (2) }

ReturnErrorProblem	::=	INTEGER {		unrecognizedInvokeID (0),
								returnErrorUnexpected (1),
								unrecognizedError (2),
								unexpectedError (3),
								mistypedParameter (4) }



--END


Bss-APDU ::=  SEQUENCE {
            protocolId		ProtocolId,
            signalInfo           SignalInfo, 
            extensionContainer   ExtensionContainer OPTIONAL 
            } 

SignalInfo2 ::= OCTET STRING (  SIZE (1 .. 2560 ) )

SupportedCamelPhases ::= BIT STRING {
  phase1  (0 ), 
  phase2  (1 ),
  phase3  (2 ),
  phase4  (3 )}


--updateLocation OPERATION
--   ARGUMENT

UpdateLocationArg ::= SEQUENCE {
	imsi							IMSI,
	msc-Number						[1] IMPLICIT ISDN-AddressString,
	vlr-Number						ISDN-AddressString,
	lmsi							[10] IMPLICIT LMSI OPTIONAL,
	extensionContainer				ExtensionContainer OPTIONAL,
	vlr-Capability					[6] IMPLICIT VLR-Capability OPTIONAL,
	informPreviousNetworkEntity		[11] IMPLICIT NULL OPTIONAL,
	cs-LCS-NotSupportedByUE			[12] IMPLICIT NULL OPTIONAL,
	v-gmlc-Address					[2] IMPLICIT GSN-Address OPTIONAL,
	add-info						[13] IMPLICIT ADD-Info OPTIONAL }

--   RESULT
UpdateLocationRes ::= SEQUENCE {
	hlr-Number				ISDN-AddressString,
	extensionContainer		ExtensionContainer OPTIONAL,

add-Capability NULL OPTIONAL }
--   ERRORS {
-- systemFailure   localValue : 34, 
-- dataMissing   localValue : 35, 
-- unexpectedDataValue   localValue : 36, 
-- unknownSubscriber   localValue : 1, 
-- roamingNotAllowed   localValue : 8}
-- ::= localValue : 2

VLR-Capability ::= SEQUENCE{
	supportedCamelPhases							[0] IMPLICIT SupportedCamelPhases OPTIONAL,
	extensionContainer								ExtensionContainer OPTIONAL,
	solsaSupportIndicator							[2] IMPLICIT NULL OPTIONAL,
	istSupportIndicator								[1] IMPLICIT IST-SupportIndicator OPTIONAL,
	superChargerSupportedInServingNetworkEntity		[3] SuperChargerInfo OPTIONAL,
	longFTN-Supported								[4] IMPLICIT NULL OPTIONAL,
	supportedLCS-CapabilitySets						[5] IMPLICIT SupportedLCS-CapabilitySets OPTIONAL,
	offeredCamel4CSIs								[6] IMPLICIT OfferedCamel4CSIs OPTIONAL }

SuperChargerInfo ::= CHOICE {
	sendSubscriberData		[0] IMPLICIT NULL,
	subscriberDataStored	[1] IMPLICIT AgeIndicator }

AgeIndicator ::= OCTET STRING (SIZE (1..6))
-- The internal structure of this parameter is implementation specific.

IST-SupportIndicator ::= ENUMERATED {
	basicISTSupported (0),
	istCommandSupported (1)}
-- exception handling:
-- reception of values > 1 shall be mapped to ' istCommandSupported '
SupportedLCS-CapabilitySets ::= BIT STRING {
	lcsCapabilitySet1 (0),
	lcsCapabilitySet2 (1),
	lcsCapabilitySet3 (2),
	lcsCapabilitySet4 (3) } (SIZE (2..16))
-- Core network signalling capability set1 indicates LCS Release98 or Release99 version.
-- Core network signalling capability set2 indicates LCS Release4.
-- Core network signalling capability set3 indicates LCS Release5.
-- Core network signalling capability set4 indicates LCS Release6 or later version.
-- A node shall mark in the BIT STRING all LCS capability sets it supports.
-- If no bit is set then the sending node does not support LCS.
-- If the parameter is not sent by an VLR then the VLR may support at most capability set1.
-- If the parameter is not sent by an SGSN then no support for LCS is assumed.
-- An SGSN is not allowed to indicate support of capability set1.
-- Other bits than listed above shall be discarded.

ADD-Info ::= SEQUENCE {
	imeisv						[0] IMPLICIT IMEI,
	skipSubscriberDataUpdate	[1] IMPLICIT NULL OPTIONAL
  }


-- Wireshark adaptation 
PrivateExtensionList ::= SEQUENCE OF PrivateExtension

PrivateExtension ::=  SEQUENCE {
  extId      OBJECT IDENTIFIER,  -- MAP-EXTENSION .&extensionId
  extType    ANY OPTIONAL -- { @extId   }
} 

SLR-ArgExtensionContainer ::= SEQUENCE {
	privateExtensionList	[0] IMPLICIT PrivateExtensionList OPTIONAL,
	slr-Arg-PCS-Extensions	[1] IMPLICIT SLR-Arg-PCS-Extensions OPTIONAL}
PcsExtensions ::= SEQUENCE {     
 }

SLR-Arg-PCS-Extensions ::= SEQUENCE {
	na-ESRK-Request [0] IMPLICIT NULL OPTIONAL }

Teleservice ::= OCTET STRING ( SIZE( 1 .. 5 ) )
Bearerservice ::= OCTET STRING ( SIZE( 1 .. 5 ) )
Msc-Number  ::= OCTET STRING ( SIZE( 1 .. 20 ) ) ( SIZE( 1 .. 9 ) ) 
-- End Wireshark adaptation 


--cancelLocation OPERATION
--   ARGUMENT

CancelLocationArg ::= [3] IMPLICIT SEQUENCE {
	identity			Identity,
	cancellationType	CancellationType OPTIONAL,
	extensionContainer	ExtensionContainer OPTIONAL}

--   V2 ARGUMENT

CancelLocationArgV2 ::= CHOICE {
	imsi			IMSI,
	imsi-WithLMSI	IMSI-WithLMSI}

--   RESULT

CancelLocationRes ::= SEQUENCE {
         extensionContainer   ExtensionContainer OPTIONAL
         }
--   ERRORS {
-- dataMissing   localValue : 35, 
-- unexpectedDataValue   localValue : 36}
-- ::= localValue : 3

CancellationType ::= ENUMERATED {
	updateProcedure (0),
	subscriptionWithdraw (1)
  }
-- The HLR shall not send values other than listed above



--purgeMS    OPERATION
--   ARGUMENT
PurgeMSArg ::= [3] IMPLICIT SEQUENCE {
         imsi                 IMSI, 
         vlr-Number           [0] IMPLICIT ISDN-AddressString OPTIONAL, 
         sgsn-Number          [1] IMPLICIT ISDN-AddressString OPTIONAL, 
         extensionContainer   ExtensionContainer OPTIONAL
         }
--   RESULT
PurgeMSRes ::= SEQUENCE {
         freezeTMSI           [0] IMPLICIT NULL OPTIONAL, 
         freezeP-TMSI         [1] IMPLICIT NULL OPTIONAL, 
         extensionContainer   ExtensionContainer OPTIONAL
         }
--   ERRORS {
-- dataMissing   localValue : 35, 
-- unexpectedDataValue   localValue : 36, 
-- unknownSubscriber   localValue : 1}
-- ::= localValue : 67

--sendIdentification OPERATION
--   ARGUMENT
SendIdentificationArg ::= SEQUENCE {
	tmsi			TMSI,
	numberOfRequestedVectors NumberOfRequestedVectors OPTIONAL,
-- within a dialogue numberOfRequestedVectors shall be present in
-- the first service request and shall not be present in subsequent service requests.
-- If received in a subsequent service request it shall be discarded.
	segmentationProhibited NULL OPTIONAL,
	extensionContainer ExtensionContainer OPTIONAL,
	msc-Number		ISDN-AddressString OPTIONAL,
	previous-LAI	[0] IMPLICIT LAIFixedLength OPTIONAL,
	hopCounter		[1] IMPLICIT HopCounter OPTIONAL }

HopCounter ::= INTEGER (0..3)

 
--   RESULT
SendIdentificationRes ::= [3] IMPLICIT SEQUENCE {
	imsi						IMSI OPTIONAL,
-- IMSI shall be present in the first (or only) service response of a dialogue.
-- If multiple service requests are present in a dialogue then IMSI
-- shall not be present in any service response other than the first one.
-- 
	authenticationSetList	AuthenticationSetList OPTIONAL,
	currentSecurityContext	[2] IMPLICIT CurrentSecurityContext OPTIONAL,
	extensionContainer		[3] IMPLICIT ExtensionContainer OPTIONAL
  }

AuthenticationSetList ::= CHOICE {
	tripletList			[0] IMPLICIT TripletList,
	quintupletList		[1] IMPLICIT QuintupletList }

TripletList ::= SEQUENCE SIZE (1..5) OF
		AuthenticationTriplet

QuintupletList ::= SEQUENCE SIZE (1..5) OF
		AuthenticationQuintuplet

AuthenticationTriplet ::= SEQUENCE {
	rand	RAND,
	sres	SRES,
	kc		Kc
  }

AuthenticationQuintuplet ::= SEQUENCE {
	rand	RAND,
	xres	XRES,
	ck		CK,
	ik		IK,
	autn	AUTN
  }

CurrentSecurityContext ::= CHOICE {
	gsm-SecurityContextData		[0] IMPLICIT GSM-SecurityContextData,
	umts-SecurityContextData	[1] IMPLICIT UMTS-SecurityContextData }

GSM-SecurityContextData ::= SEQUENCE {
	kc		Kc,
	cksn	Cksn
  }

UMTS-SecurityContextData ::= SEQUENCE {
	ck		CK,
	ik		IK,
	ksi		KSI
  }

RAND ::= OCTET STRING (SIZE (16))

SRES ::= OCTET STRING (SIZE (4))

Kc ::= OCTET STRING (SIZE (8))

XRES ::= OCTET STRING (SIZE (4..16))

CK ::= OCTET STRING (SIZE (16))

IK ::= OCTET STRING (SIZE (16))

AUTN ::= OCTET STRING (SIZE (16))

AUTS ::= OCTET STRING (SIZE (14))

Cksn ::= OCTET STRING (SIZE (1))
-- The internal structure is defined in 3GPP TS 24.008

KSI ::= OCTET STRING (SIZE (1))
-- The internal structure is defined in 3GPP TS 24.008

--   ERRORS {
-- dataMissing   localValue : 35, 
-- unidentifiedSubscriber   localValue : 5}
-- ::= localValue : 55

--prepareHandover OPERATION
--   ARGUMENT
PrepareHO-Arg ::= SEQUENCE {
         targetCellId           GlobalCellId OPTIONAL, 
         ho-NumberNotRequired   NULL OPTIONAL, 
         bss-APDU               Bss-APDU OPTIONAL
         }
--   RESULT
-- V3 def: ?
-- prepareHandover OPERATION  ::=  {
--   ARGUMENT     [3] IMPLICIT SEQUENCE {
PrepareHO-ArgV3 ::= [3] IMPLICIT SEQUENCE {
	targetCellId						[0] IMPLICIT GlobalCellId OPTIONAL,
	ho-NumberNotRequired				NULL OPTIONAL,
	targetRNCId							[1] IMPLICIT RNCId OPTIONAL,
	an-APDU								[2] IMPLICIT AccessNetworkSignalInfo OPTIONAL,
	multipleBearerRequested				[3] IMPLICIT NULL OPTIONAL,
	imsi								[4] IMPLICIT IMSI OPTIONAL,
	integrityProtectionInfo				[5] IMPLICIT IntegrityProtectionInformation OPTIONAL,
	encryptionInfo						[6] IMPLICIT EncryptionInformation OPTIONAL,
	radioResourceInformation			[7] IMPLICIT RadioResourceInformation OPTIONAL,
	allowedGSM-Algorithms				[9] IMPLICIT AllowedGSM-Algorithms OPTIONAL,
	allowedUMTS-Algorithms				[10] IMPLICIT AllowedUMTS-Algorithms OPTIONAL,
	radioResourceList					[11] IMPLICIT RadioResourceList OPTIONAL,
	extensionContainer					[8] IMPLICIT ExtensionContainer OPTIONAL,
	rab-Id								[12] IMPLICIT RAB-Id OPTIONAL,
	bssmap-ServiceHandover				[13] IMPLICIT BSSMAP-ServiceHandover OPTIONAL,
	ranap-ServiceHandover				[14] IMPLICIT RANAP-ServiceHandover OPTIONAL,
	bssmap-ServiceHandoverList			[15] IMPLICIT BSSMAP-ServiceHandoverList OPTIONAL,
	asciCallReference					[20] IMPLICIT ASCI-CallReference OPTIONAL,
	geran-classmark						[16] IMPLICIT GERAN-Classmark OPTIONAL,
	iuCurrentlyUsedCodec				[17] IMPLICIT Codec OPTIONAL,
	iuSupportedCodecsList				[18] IMPLICIT SupportedCodecsList OPTIONAL,
	rab-ConfigurationIndicator			[19] IMPLICIT NULL OPTIONAL,
	uesbi-Iu							[21] IMPLICIT UESBI-Iu OPTIONAL,
	imeisv								[22] IMPLICIT IMEI OPTIONAL }

BSSMAP-ServiceHandoverList ::= SEQUENCE SIZE (1.. 7) OF
BSSMAP-ServiceHandoverInfo

BSSMAP-ServiceHandoverInfo ::= SEQUENCE {
	bssmap-ServiceHandover	BSSMAP-ServiceHandover,
	rab-Id					RAB-Id
-- RAB Identity is needed to relate the service handovers with the radio access bearers.
  }

BSSMAP-ServiceHandover ::= OCTET STRING (SIZE (1))
-- Octets are coded according the Service Handover information element in
-- 3GPP TS 48.008.

RANAP-ServiceHandover ::= OCTET STRING (SIZE (1))
-- Octet contains a complete Service-Handover data type
-- as defined in 3GPP TS 25.413, encoded according to the encoding scheme
-- mandated by 3GPP TS 25.413
-- Padding bits are included in the least significant bits.

RadioResourceList ::= SEQUENCE SIZE (1.. maxNumOfRadioResources) OF
RadioResource

RadioResource ::= SEQUENCE {
	radioResourceInformation	RadioResourceInformation,
	rab-Id						RAB-Id
-- RAB Identity is needed to relate the radio resources with the radio access bearers.
  }



PrepareHO-Res ::= SEQUENCE {
         handoverNumber   ISDN-AddressString OPTIONAL, 
         bss-APDU         Bss-APDU OPTIONAL
         }

HandoverNumber ::= OCTET STRING ( SIZE( 1 .. 20 ) ) ( SIZE( 1 .. 9 ) )

PrepareHO-ResV3 ::= [3] IMPLICIT SEQUENCE {
	handoverNumber						[0] IMPLICIT ISDN-AddressString OPTIONAL,
	relocationNumberList				[1] IMPLICIT RelocationNumberList OPTIONAL,
	an-APDU								[2] IMPLICIT AccessNetworkSignalInfo OPTIONAL,
	multicallBearerInfo					[3] IMPLICIT MulticallBearerInfo OPTIONAL,
	multipleBearerNotSupported			NULL OPTIONAL,
	selectedUMTS-Algorithms				[5] IMPLICIT SelectedUMTS-Algorithms OPTIONAL,
	chosenRadioResourceInformation		[6] IMPLICIT ChosenRadioResourceInformation OPTIONAL,
	extensionContainer					[4] IMPLICIT ExtensionContainer OPTIONAL,
	iuSelectedCodec						[7] Codec OPTIONAL,
	iuAvailableCodecsList				[8] CodecList OPTIONAL }
--   ERRORS {
-- systemFailure   localValue : 34, 
-- dataMissing   localValue : 35, 
-- unexpectedDataValue   localValue : 36, 
-- noAvailable   localValue : 25}
-- ::= localValue : 68

SelectedUMTS-Algorithms ::= SEQUENCE {
	integrityProtectionAlgorithm	[0] IMPLICIT ChosenIntegrityProtectionAlgorithm OPTIONAL,
	encryptionAlgorithm				[1] IMPLICIT ChosenEncryptionAlgorithm OPTIONAL,
	extensionContainer				[2] IMPLICIT ExtensionContainer OPTIONAL
  }

ChosenIntegrityProtectionAlgorithm ::= OCTET STRING (SIZE (1))
-- Octet contains a complete IntegrityProtectionAlgorithm data type
-- as defined in 3GPP TS 25.413, encoded according to the encoding scheme
-- mandated by 3GPP TS 25.413
-- Padding bits are included in the least significant bits.

ChosenEncryptionAlgorithm ::= OCTET STRING (SIZE (1))
-- Octet contains a complete EncryptionAlgorithm data type
-- as defined in 3GPP TS 25.413, encoded according to the encoding scheme
-- mandated by 3GPP TS 25.413
-- Padding bits are included in the least significant bits.

ChosenRadioResourceInformation ::= SEQUENCE {
	chosenChannelInfo			[0] IMPLICIT ChosenChannelInfo OPTIONAL,
	chosenSpeechVersion			[1] IMPLICIT ChosenSpeechVersion OPTIONAL
  }

ChosenChannelInfo ::= OCTET STRING (SIZE (1))
-- Octets are coded according the Chosen Channel information element in 3GPP TS 48.008

ChosenSpeechVersion ::= OCTET STRING (SIZE (1))
-- Octets are coded according the Speech Version (chosen) information element in 3GPP TS
-- 48.008



ProtocolId ::=         ENUMERATED {
               gsm-0408        ( 1 ), 
               gsm-0806        ( 2 ), 
               gsm-BSSMAP      ( 3 ), 
               ets-300102-1    ( 4 ) 
}

Sgsn-Number ::= OCTET STRING ( SIZE( 1 .. 20 ) ) ( SIZE( 1 .. 9 ) ) 
Vlr-Number ::= OCTET STRING ( SIZE( 1 .. 20 ) ) ( SIZE( 1 .. 9 ) )
-- End Wireshark adaptation --
--sendEndSignal OPERATION
--   ARGUMENT
--Bss-APDU ::=  SEQUENCE { ... defined elsewhere
-- ::= localValue : 29
-- V9 ???
--sendEndSignal OPERATION  ::=  {
--   ARGUMENT     [3] IMPLICIT SEQUENCE {
--      an-APDU              
--    :

SendEndSignalArgV3 ::= [3] IMPLICIT SEQUENCE {
	an-APDU					AccessNetworkSignalInfo,
	extensionContainer		[0] IMPLICIT ExtensionContainer OPTIONAL
  }

SendEndSignalRes ::= SEQUENCE {
	extensionContainer	[0] IMPLICIT ExtensionContainer OPTIONAL
  }

RNCId ::= OCTET STRING (SIZE (7))
-- The internal structure is defined as follows:
-- octet 1 bits 4321 Mobile Country Code 1st digit
-- bits 8765 Mobile Country Code 2nd digit
-- octet 2 bits 4321 Mobile Country Code 3rd digit
-- bits 8765 Mobile Network Code 3rd digit
-- or filler (1111) for 2 digit MNCs
-- octet 3 bits 4321 Mobile Network Code 1st digit
-- bits 8765 Mobile Network Code 2nd digit
-- octets 4 and 5 Location Area Code according to 3GPP TS 24.008
-- octets 6 and 7 RNC Id value according to 3GPP TS 25.413

RelocationNumberList ::= SEQUENCE SIZE (1..7) OF
RelocationNumber

MulticallBearerInfo ::= INTEGER (1..7)

RelocationNumber ::= SEQUENCE {
	handoverNumber		ISDN-AddressString,
	rab-Id				RAB-Id
-- RAB Identity is needed to relate the calls with the radio access bearers.
  }

RAB-Id ::= INTEGER (1..255)

RadioResourceInformation ::= OCTET STRING (SIZE (3..13))
-- Octets are coded according the Channel Type information element in 3GPP TS 48.008

IntegrityProtectionInformation ::= OCTET STRING (SIZE (18..100))
-- Octets contain a complete IntegrityProtectionInformation data type
-- as defined in 3GPP TS 25.413, encoded according to the encoding scheme
-- mandated by 3GPP TS 25.413
-- Padding bits are included, if needed, in the least significant bits of the
-- last octet of the octet string.

EncryptionInformation ::= OCTET STRING (SIZE (18..100))
-- Octets contain a complete EncryptionInformation data type
-- as defined in 3GPP TS 25.413, encoded according to the encoding scheme
-- mandated by 3GPP TS 25.413
-- Padding bits are included, if needed, in the least significant bits of the
-- last octet of the octet string.


--processAccessSignalling OPERATION
--   ARGUMENT
--Bss-APDU ::=  SEQUENCE { ... defined elsewhere
-- ::= localValue : 33

ProcessAccessSignallingArgV3 ::= [3] IMPLICIT SEQUENCE {
	an-APDU							AccessNetworkSignalInfo,
	selectedUMTS-Algorithms			[1] IMPLICIT SelectedUMTS-Algorithms OPTIONAL,
	selectedGSM-Algorithm			[2] IMPLICIT SelectedGSM-Algorithm OPTIONAL,
	chosenRadioResourceInformation	[3] IMPLICIT ChosenRadioResourceInformation OPTIONAL,
	selectedRab-Id					[4] IMPLICIT RAB-Id OPTIONAL,
	extensionContainer				[0] IMPLICIT ExtensionContainer OPTIONAL,
	iUSelectedCodec					[5] IMPLICIT Codec OPTIONAL,
	iuAvailableCodecsList			[6] IMPLICIT CodecList OPTIONAL }

SupportedCodecsList ::= SEQUENCE {
	utranCodecList			[0] IMPLICIT CodecList OPTIONAL,
	geranCodecList			[1] IMPLICIT CodecList OPTIONAL,
	extensionContainer		[2] IMPLICIT ExtensionContainer OPTIONAL
  }

CodecList ::= SEQUENCE {
	codec1					[1] IMPLICIT Codec,
	codec2					[2] IMPLICIT Codec OPTIONAL,
	codec3					[3] IMPLICIT Codec OPTIONAL,
	codec4					[4] IMPLICIT Codec OPTIONAL,
	codec5					[5] IMPLICIT Codec OPTIONAL,
	codec6					[6] IMPLICIT Codec OPTIONAL,
	codec7					[7] IMPLICIT Codec OPTIONAL,
	codec8					[8] IMPLICIT Codec OPTIONAL,
	extensionContainer		[9] IMPLICIT ExtensionContainer OPTIONAL
  }
-- Codecs are sent in priority order where codec1 has highest priority

Codec ::= OCTET STRING (SIZE (1..4))
-- The internal structure is defined as follows:
-- octet 1 Coded as Codec Identification code in 3GPP TS 26.103
-- octets 2,3,4 Parameters for the Codec as defined in 3GPP TS
-- 26.103, if available, length depending on the codec

GERAN-Classmark ::= OCTET STRING (SIZE (2..87))
-- Octets are coded according the GERAN Classmark information element in 3GPP TS 48.008

SelectedGSM-Algorithm ::= OCTET STRING (SIZE (1))
-- internal structure is coded as Algorithm identifier octet from Chosen Encryption
-- Algorithm defined in 3GPP TS 48.008
-- A node shall mark only the selected GSM algorithm


--forwardAccessSignalling OPERATION
--   ARGUMENT

ForwardAccessSignallingArgV3 ::= [3] SEQUENCE {
	an-APDU							AccessNetworkSignalInfo,
	integrityProtectionInfo			[0] IntegrityProtectionInformation OPTIONAL,
	encryptionInfo					[1] EncryptionInformation OPTIONAL,
	keyStatus						[2] KeyStatus OPTIONAL,
	allowedGSM-Algorithms			[4] AllowedGSM-Algorithms OPTIONAL,
	allowedUMTS-Algorithms			[5] AllowedUMTS-Algorithms OPTIONAL,
	radioResourceInformation		[6] RadioResourceInformation OPTIONAL,
	extensionContainer				[3] ExtensionContainer OPTIONAL,
	radioResourceList				[7] RadioResourceList OPTIONAL,
	bssmap-ServiceHandover			[9] BSSMAP-ServiceHandover OPTIONAL,
	ranap-ServiceHandover			[8] RANAP-ServiceHandover OPTIONAL,
	bssmap-ServiceHandoverList		[10] BSSMAP-ServiceHandoverList OPTIONAL,
	currentlyUsedCodec				[11] Codec OPTIONAL,
	iuSupportedCodecsList			[12] SupportedCodecsList OPTIONAL,
	rab-ConfigurationIndicator		[13] NULL OPTIONAL,
	iuSelectedCodec					[14] Codec OPTIONAL }

--Bss-APDU ::=  SEQUENCE { ... defined elsewhere
-- ::= localValue : 34

AllowedGSM-Algorithms ::= OCTET STRING (SIZE (1))
-- internal structure is coded as Algorithm identifier octet from
-- Permitted Algorithms defined in 3GPP TS 48.008
-- A node shall mark all GSM algorithms that are allowed in MSC-B

AllowedUMTS-Algorithms ::= SEQUENCE {
	integrityProtectionAlgorithms	[0] IMPLICIT PermittedIntegrityProtectionAlgorithms OPTIONAL,
	encryptionAlgorithms			[1] IMPLICIT PermittedEncryptionAlgorithms OPTIONAL,
	extensionContainer				[2] IMPLICIT ExtensionContainer OPTIONAL
  }

PermittedIntegrityProtectionAlgorithms ::= OCTET STRING (SIZE (1..9))
-- Octets contain a complete PermittedIntegrityProtectionAlgorithms data type
-- as defined in 3GPP TS 25.413, encoded according to the encoding scheme
-- mandated by 3GPP TS 25.413.
-- Padding bits are included, if needed, in the least significant bits of the
-- last octet of the octet string.

PermittedEncryptionAlgorithms ::= OCTET STRING (SIZE (1..9))
-- Octets contain a complete PermittedEncryptionAlgorithms data type
-- as defined in 3GPP TS 25.413, encoded according to the encoding scheme
-- mandated by 3GPP TS 25.413
-- Padding bits are included, if needed, in the least significant bits of the
-- last octet of the octet string.

KeyStatus ::= ENUMERATED {
	old (0),
	new (1)
  }
-- exception handling:
-- received values in range 2-31 shall be treated as "old"
-- received values greater than 31 shall be treated as "new"



--prepareSubsequentHandover OPERATION
--   ARGUMENT
PrepareSubsequentHOArg ::= SEQUENCE {
         targetCellId       GlobalCellId, 
         targetMSC-Number   ISDN-AddressString, 
         bss-APDU           Bss-APDU
         }

PrepareSubsequentHOArgV3 ::= [3] SEQUENCE {
	targetCellId				[0] IMPLICIT GlobalCellId OPTIONAL,
	targetMSC-Number			[1] IMPLICIT ISDN-AddressString,
	targetRNCId					[2] IMPLICIT RNCId OPTIONAL,
	an-APDU						[3] IMPLICIT AccessNetworkSignalInfo OPTIONAL,
	selectedRab-Id				[4] IMPLICIT RAB-Id OPTIONAL,
	extensionContainer			[5] IMPLICIT ExtensionContainer OPTIONAL,
	geran-classmark				[6] IMPLICIT GERAN-Classmark OPTIONAL,
	rab-ConfigurationIndicator	[7] IMPLICIT NULL OPTIONAL }

--   RESULT
--bss-APDU ::=  SEQUENCE {  ... defined elsewhere
PrepareSubsequentHOResV3 ::= [3] IMPLICIT SEQUENCE {
	an-APDU					AccessNetworkSignalInfo,
	extensionContainer		[0] IMPLICIT ExtensionContainer OPTIONAL
  }

--   ERRORS {
-- unexpectedDataValue   localValue : 36, 
-- dataMissing   localValue : 35, 
-- unknownMSC   localValue : 3, 
-- subsequentHandoverFailure   localValue : 26}
-- ::= localValue : 69

--sendAuthenticationInfo OPERATION
--   ARGUMENT

SendAuthenticationInfoArg ::= IMSI

SendAuthenticationInfoArgV2 ::= SEQUENCE {
	imsi						[0] IMPLICIT IMSI,
	numberOfRequestedVectors	NumberOfRequestedVectors,
	segmentationProhibited		NULL OPTIONAL,
	immediateResponsePreferred	[1] IMPLICIT NULL OPTIONAL,
	re-synchronisationInfo		Re-synchronisationInfo OPTIONAL,
	extensionContainer			[2] IMPLICIT ExtensionContainer OPTIONAL,
	requestingNodeType			[3] IMPLICIT RequestingNodeType OPTIONAL,
	requestingPLMN-Id			[4] IMPLICIT PLMN-Id OPTIONAL }

--   RESULT

SendAuthenticationInfoRes ::= SEQUENCE OF
         SEQUENCE {
            rand       RAND, 
            sres       SRES, 
            kc         Kc
            }

--   RESULT     [3] IMPLICIT SEQUENCE {

SendAuthenticationInfoResV3 ::= [3] IMPLICIT SEQUENCE {
	authenticationSetList		AuthenticationSetList OPTIONAL,
	extensionContainer			ExtensionContainer OPTIONAL
  }
--   ERRORS {
-- systemFailure   localValue : 34, 
-- dataMissing   localValue : 35, 
-- unexpectedDataValue   localValue : 36, 
-- unknownSubscriber   localValue : 1}
-- ::= localValue : 56

PLMN-Id ::= OCTET STRING (SIZE (3))
-- The internal structure is defined as follows:
-- octet 1 bits 4321 Mobile Country Code 1st digit
-- bits 8765 Mobile Country Code 2nd digit
-- octet 2 bits 4321 Mobile Country Code 3rd digit
-- bits 8765 Mobile Network Code 3rd digit
-- or filler (1111) for 2 digit MNCs
-- octet 3 bits 4321 Mobile Network Code 1st digit
-- bits 8765 Mobile Network Code 2nd digit

NumberOfRequestedVectors ::= INTEGER (1..5)

Re-synchronisationInfo ::= SEQUENCE {
	rand RAND,
	auts AUTS
  }

RequestingNodeType ::= ENUMERATED {
	vlr (0),
	sgsn (1)
  }
-- exception handling:
-- received values in the range 2-15 shall be treated as "vlr"
-- received values greater than 15 shall be treated as "sgsn"

--checkIMEI  OPERATION
--   ARGUMENT
-- CheckIMEIArg ::= IMEI 
-- calling dissect_gsm_map_IMEI directly from template


-- V3
-- checkIMEI  OPERATION  ::=  {
--   ARGUMENT     SEQUENCE {

CheckIMEIArgV3 ::= SEQUENCE {
	imei IMEI,
	requestedEquipmentInfo	RequestedEquipmentInfo,
	extensionContainer	ExtensionContainer OPTIONAL
}

--	RESULT
--	equipmentStatus EquipmentStatus

-- V3
--   RESULT     SEQUENCE {
CheckIMEIRes ::= SEQUENCE {
	equipmentStatus			EquipmentStatus OPTIONAL,
	bmuef					UESBI-Iu OPTIONAL,
	extensionContainer		[0] ExtensionContainer OPTIONAL
  }

RequestedEquipmentInfo::= BIT STRING {
	equipmentStatus (0),
	bmuef (1)} (SIZE (2..8))
-- exception handling: reception of unknown bit assignments in the
-- RequestedEquipmentInfo data type shall be discarded by the receiver

UESBI-Iu ::= SEQUENCE {
	uesbi-IuA [0] IMPLICIT UESBI-IuA OPTIONAL,
	uesbi-IuB [1] IMPLICIT UESBI-IuB OPTIONAL
  }

UESBI-IuA ::= BIT STRING (SIZE(1..128))
-- See 3GPP TS 25.413

UESBI-IuB ::= BIT STRING (SIZE(1..128))
-- See 3GPP TS 25.413

EquipmentStatus ::= ENUMERATED {
         whiteListed    ( 0 ), 
         blackListed    ( 1 ), 
         greyListed     ( 2 ) }
--   ERRORS {
-- systemFailure   localValue : 34, 
-- dataMissing   localValue : 35, 
-- unknownEquipment   localValue : 7}
-- ::= localValue : 43


OverrideCategory ::= ENUMERATED {
   overrideEnabled     ( 0 ), 
   overrideDisabled    ( 1 ) }

BasicService ::= CHOICE {
  bearerservice     [2] IMPLICIT Bearerservice, 
  teleservice       [3] IMPLICIT Teleservice}

BasicServiceGroupList ::= SEQUENCE OF BasicService

ODB-GeneralData ::= BIT STRING {
	allOG-CallsBarred (0),
	internationalOGCallsBarred (1),
	internationalOGCallsNotToHPLMN-CountryBarred (2),
	interzonalOGCallsBarred (6),
	interzonalOGCallsNotToHPLMN-CountryBarred (7),
	interzonalOGCallsAndInternationalOGCallsNotToHPLMN-CountryBarred (8),
	premiumRateInformationOGCallsBarred (3),
	premiumRateEntertainementOGCallsBarred (4),
	ss-AccessBarred (5),
	allECT-Barred (9),
	chargeableECT-Barred (10),
	internationalECT-Barred (11),
	interzonalECT-Barred (12),
	doublyChargeableECT-Barred (13),
	multipleECT-Barred (14),
	allPacketOrientedServicesBarred (15),
	roamerAccessToHPLMN-AP-Barred (16),
	roamerAccessToVPLMN-AP-Barred (17),
	roamingOutsidePLMNOG-CallsBarred (18),
	allIC-CallsBarred (19),
	roamingOutsidePLMNIC-CallsBarred (20),
	roamingOutsidePLMNICountryIC-CallsBarred (21),
	roamingOutsidePLMN-Barred (22),
	roamingOutsidePLMN-CountryBarred (23),
	registrationAllCF-Barred (24),
	registrationCFNotToHPLMN-Barred (25),
	registrationInterzonalCF-Barred (26),
	registrationInterzonalCFNotToHPLMN-Barred (27),
	registrationInternationalCF-Barred (28)}

ODB-HPLMN-Data ::= BIT STRING {
  plmn-SpecificBarringType1  (0 ), 
  plmn-SpecificBarringType2  (1 ), 
  plmn-SpecificBarringType3  (2 ), 
  plmn-SpecificBarringType4  (3 )}

SubscriberStatus ::= ENUMERATED {
  serviceGranted               ( 0 ), 
  operatorDeterminedBarring    ( 1 ) }

BcsmTriggerDetectionPoint ::= ENUMERATED {
  collectedInfo				( 2 ), 
  routeSelectFailure		(4 ),
  termAttemptAuthorized		( 12 ), 
  tBusy						(13 ), 
  tNoAnswer					(14 )
  }

ServiceKey ::= INTEGER ( 0 .. 2147483647 )

BcsmCamelTDPData ::= SEQUENCE {
  bcsmTriggerDetectionPoint   BcsmTriggerDetectionPoint, 
  serviceKey                    ServiceKey, 
  gsmSCFAddress                [0] IMPLICIT GsmSCF-Address, 
  defaultCallHandling           [1] IMPLICIT DefaultCallHandling, 
  extensionContainer            [2] IMPLICIT ExtensionContainer OPTIONAL
  }

BcsmCamelTDPDataList ::= SEQUENCE OF BcsmCamelTDPData

GsmSCF-Address ::= OCTET STRING ( SIZE( 1 .. 20 ) ) ( SIZE( 1 .. 9 ) )

DefaultCallHandling ::= ENUMERATED {
  continueCall    ( 0 ), 
  releaseCall     ( 1 )
  }

O-CSI ::= SEQUENCE {
	o-BcsmCamelTDPDataList			O-BcsmCamelTDPDataList,
	extensionContainer				ExtensionContainer OPTIONAL,
	camelCapabilityHandling			[0] IMPLICIT CamelCapabilityHandling OPTIONAL,
	notificationToCSE				[1] IMPLICIT NULL OPTIONAL,
	csiActive						[2] IMPLICIT NULL OPTIONAL}
-- notificationtoCSE and csiActive shall not be present when O-CSI is sent to VLR/GMSC.
-- They may only be included in ATSI/ATM ack/NSDC message.
-- O-CSI shall not be segmented.

O-BcsmCamelTDPDataList ::= SEQUENCE SIZE (1..10) OF
O-BcsmCamelTDPData
-- O-BcsmCamelTDPDataList shall not contain more than one instance of
-- O-BcsmCamelTDPData containing the same value for o-BcsmTriggerDetectionPoint.
-- For CAMEL Phase 2, this means that only one instance of O-BcsmCamelTDPData is allowed
-- with o-BcsmTriggerDetectionPoint being equal to DP2.

O-BcsmCamelTDPData ::= SEQUENCE {
	o-BcsmTriggerDetectionPoint		O-BcsmTriggerDetectionPoint,
	serviceKey						ServiceKey,
	gsmSCF-Address					[0] IMPLICIT ISDN-AddressString,
	defaultCallHandling				[1] IMPLICIT DefaultCallHandling,
	extensionContainer				[2] IMPLICIT ExtensionContainer OPTIONAL
}

ISDN-AddressString ::= OCTET STRING

--insertSubscriberData OPERATION
--   ARGUMENT
InsertSubscriberDataArg ::= SEQUENCE {
	imsi							[0] IMPLICIT IMSI OPTIONAL,
    msisdn                          [1] IMPLICIT ISDN-AddressString OPTIONAL, 
	category						[2] IMPLICIT Category OPTIONAL,
	subscriberStatus				[3] IMPLICIT SubscriberStatus OPTIONAL,
    bearerserviceList               [4] IMPLICIT BearerServiceList OPTIONAL, 
	teleserviceList					[6] IMPLICIT TeleserviceList OPTIONAL,
	provisionedSS					[7] IMPLICIT Ext-SS-InfoList OPTIONAL,
	odb-Data						[8] IMPLICIT ODB-Data OPTIONAL,
	roamingRestrictionDueToUnsupportedFeature [9] IMPLICIT NULL OPTIONAL,
	regionalSubscriptionData		[10] IMPLICIT ZoneCodeList OPTIONAL,
	vbsSubscriptionData				[11] IMPLICIT VBSDataList OPTIONAL,
	vgcsSubscriptionData			[12] IMPLICIT VGCSDataList OPTIONAL,
	vlrCamelSubscriptionInfo		[13] IMPLICIT VlrCamelSubscriptionInfo OPTIONAL,
	extensionContainer				[14] IMPLICIT ExtensionContainer OPTIONAL,
	naea-PreferredCI				[15] IMPLICIT NAEA-PreferredCI OPTIONAL,
--	naea-PreferredCI is included at the discretion of the HLR operator.
	gprsSubscriptionData			[16] IMPLICIT GPRSSubscriptionData OPTIONAL,
	roamingRestrictedInSgsnDueToUnsupportedFeature [23] IMPLICIT NULL OPTIONAL,
	networkAccessMode				[24] IMPLICIT NetworkAccessMode OPTIONAL,
	lsaInformation					[25] IMPLICIT LSAInformation OPTIONAL,
	lmu-Indicator					[21] IMPLICIT NULL OPTIONAL,
	lcsInformation					[22] IMPLICIT LCSInformation OPTIONAL,
	istAlertTimer					[26] IMPLICIT IST-AlertTimerValue OPTIONAL,
	superChargerSupportedInHLR		[27] IMPLICIT AgeIndicator OPTIONAL,
	mc-SS-Info						[28] IMPLICIT MC-SS-Info OPTIONAL,
	cs-AllocationRetentionPriority	[29] IMPLICIT CS-AllocationRetentionPriority OPTIONAL,
	sgsn-CAMEL-SubscriptionInfo		[17] IMPLICIT SGSN-CAMEL-SubscriptionInfo OPTIONAL,
	chargingCharacteristics			[18] IMPLICIT ChargingCharacteristics OPTIONAL,
	accessRestrictionData			[19] IMPLICIT AccessRestrictionData OPTIONAL
}
-- If the Network Access Mode parameter is sent, it shall be present only in
-- the first sequence if seqmentation is used

AccessRestrictionData ::= BIT STRING {
	utranNotAllowed (0),
	geranNotAllowed (1) } (SIZE (2..8))
-- exception handling:
-- bits 2 to 7 shall be ignored if received and not understood

CS-AllocationRetentionPriority ::= OCTET STRING (SIZE (1))
-- This data type encodes each priority level defined in TS 23.107 as the binary value
-- of the priority level.

IST-AlertTimerValue ::= INTEGER (15..255)

LCSInformation ::= SEQUENCE {
	gmlc-List						[0] IMPLICIT GMLC-List OPTIONAL,
	lcs-PrivacyExceptionList		[1] IMPLICIT LCS-PrivacyExceptionList OPTIONAL,
	molr-List						[2] IMPLICIT MOLR-List OPTIONAL,
	add-lcs-PrivacyExceptionList	[3] LCS-PrivacyExceptionList OPTIONAL }
-- add-lcs-PrivacyExceptionList may be sent only if lcs-PrivacyExceptionList is
-- present and contains four instances of LCS-PrivacyClass. If the mentioned condition
-- is not satisfied the receiving node shall discard add-lcs-PrivacyExceptionList.
-- If an LCS-PrivacyClass is received both in lcs-PrivacyExceptionList and in
-- add-lcs-PrivacyExceptionList with the same SS-Code, then the error unexpected
-- data value shall be returned.

GMLC-List ::= SEQUENCE SIZE (1..5) OF ISDN-AddressString
-- if segmentation is used, the complete GMLC-List shall be sent in one segment

NetworkAccessMode ::= ENUMERATED {
	bothMSCAndSGSN (0),
	onlyMSC (1),
	onlySGSN (2)
  }
-- if unknown values are received in NetworkAccessMode
-- they shall be discarded.

GPRSDataList ::= SEQUENCE SIZE (1..50) OF PDP-Context

PDP-Context ::= SEQUENCE {
	pdp-ContextId				ContextId,
	pdp-Type					[16] IMPLICIT PDP-Type,
	pdp-Address					[17] IMPLICIT PDP-Address OPTIONAL,
	qos-Subscribed				[18] IMPLICIT QoS-Subscribed,
	vplmnAddressAllowed			[19] IMPLICIT NULL OPTIONAL,
	apn							[20] IMPLICIT APN,
	extensionContainer			[21] IMPLICIT ExtensionContainer OPTIONAL,
	ext-QoS-Subscribed			[0] IMPLICIT Ext-QoS-Subscribed OPTIONAL,
	pdp-ChargingCharacteristics [1] IMPLICIT ChargingCharacteristics OPTIONAL,
	ext2-QoS-Subscribed			[2] IMPLICIT Ext2-QoS-Subscribed OPTIONAL
-- ext2-QoS-Subscribed may be present only if ext-QoS-Subscribed is present.
}

ContextId ::= INTEGER (1..50)

GPRSSubscriptionData ::= SEQUENCE {
	completeDataListIncluded		NULL OPTIONAL,
-- If segmentation is used, completeDataListIncluded may only be present in the
-- first segment.
	gprsDataList					[1] IMPLICIT GPRSDataList,
	extensionContainer				[2] IMPLICIT ExtensionContainer OPTIONAL
  }

SGSN-CAMEL-SubscriptionInfo ::= SEQUENCE {
	gprs-CSI					[0] IMPLICIT GPRS-CSI OPTIONAL,
	mo-sms-CSI					[1] IMPLICIT SMS-CSI OPTIONAL,
	extensionContainer			[2] IMPLICIT ExtensionContainer OPTIONAL,
	mt-sms-CSI					[3] IMPLICIT SMS-CSI OPTIONAL,
	mt-smsCAMELTDP-CriteriaList [4] IMPLICIT MT-smsCAMELTDP-CriteriaList OPTIONAL,
	mg-csi						[5] IMPLICIT MG-CSI OPTIONAL
}

GPRS-CSI ::= SEQUENCE {
	gprs-CamelTDPDataList		[0] IMPLICIT GPRS-CamelTDPDataList OPTIONAL,
	camelCapabilityHandling		[1] IMPLICIT CamelCapabilityHandling OPTIONAL,
	extensionContainer			[2] IMPLICIT ExtensionContainer OPTIONAL,
	notificationToCSE			[3] IMPLICIT NULL OPTIONAL,
	csi-Active					[4] IMPLICIT NULL OPTIONAL
  }
-- notificationToCSE and csi-Active shall not be present when GPRS-CSI is sent to SGSN.
-- They may only be included in ATSI/ATM ack/NSDC message.
-- GPRS-CamelTDPData and camelCapabilityHandling shall be present in
-- the GPRS-CSI sequence.
-- If GPRS-CSI is segmented, gprs-CamelTDPDataList and camelCapabilityHandling shall be
-- present in the first segment

GPRS-CamelTDPDataList ::= SEQUENCE SIZE (1..10) OF
GPRS-CamelTDPData
-- GPRS-CamelTDPDataList shall not contain more than one instance of
-- GPRS-CamelTDPData containing the same value for gprs-TriggerDetectionPoint.

GPRS-CamelTDPData ::= SEQUENCE {
	gprs-TriggerDetectionPoint		[0] IMPLICIT GPRS-TriggerDetectionPoint,
	serviceKey						[1] IMPLICIT ServiceKey,
	gsmSCF-Address					[2] IMPLICIT ISDN-AddressString,
	defaultSessionHandling			[3] IMPLICIT DefaultGPRS-Handling,
	extensionContainer				[4] IMPLICIT ExtensionContainer OPTIONAL
}

DefaultGPRS-Handling ::= ENUMERATED {
	continueTransaction (0) ,
	releaseTransaction (1)}
-- exception handling:
-- reception of values in range 2-31 shall be treated as "continueTransaction"
-- reception of values greater than 31 shall be treated as "releaseTransaction"

GPRS-TriggerDetectionPoint ::= ENUMERATED {
	attach (1),
	attachChangeOfPosition (2),
	pdp-ContextEstablishment (11),
	pdp-ContextEstablishmentAcknowledgement (12),
	pdp-ContextChangeOfPosition (14)
  }
-- exception handling:
-- For GPRS-CamelTDPData sequences containing this parameter with any
-- other value than the ones listed the receiver shall ignore the whole
-- GPRS-CamelTDPDatasequence.

APN ::= OCTET STRING (SIZE (2..63))
-- Octets are coded according to TS 3GPP TS 23.003 [17]

PDP-Type ::= OCTET STRING (SIZE (2))
-- Octets are coded according to TS 3GPP TS 29.060 [105]

PDP-Address ::= OCTET STRING (SIZE (1..16))
-- Octets are coded according to TS 3GPP TS 29.060 [105]
-- The possible size values are:
-- 1-7 octets X.25 address type
-- 4 octets IPv4 address type
-- 16 octets Ipv6 address type

QoS-Subscribed ::= OCTET STRING (SIZE (3))
-- Octets are coded according to TS 3GPP TS 24.008 [35] Quality of Service Octets
-- 3-5.

Ext-QoS-Subscribed ::= OCTET STRING (SIZE (1..9))
-- OCTET 1:
-- Allocation/Retention Priority (This octet encodes each priority level defined in
-- 23.107 as the binary value of the priority level, declaration in 29.060)
-- Octets 2-9 are coded according to 3GPP TS 24.008[35] Quality of Service Octets
-- 6-13.

Ext2-QoS-Subscribed ::= OCTET STRING (SIZE (1..3))
-- Octets 1-3 are coded according to 3GPP TS 24.008 [35] Quality of Service Octets 14-16.
-- If Quality of Service information is structured with 14 octet length, then
-- Octet 1 is coded according to 3GPP TS 24.008 [35] Quality of Service Octet 14.

ChargingCharacteristics ::= OCTET STRING (SIZE (2))
-- Octets are coded according to 3GPP TS 32.015.
-- From 3GPP TS 32.015.
--
-- Descriptions for the bits of the flag set:
--
-- Bit 1: H (Hot billing) := '00000001'B
-- Bit 2: F (Flat rate) := '00000010'B
-- Bit 3: P (Prepaid service) := '00000100'B
-- Bit 4: N (Normal billing) := '00001000'B
-- Bit 5: - (Reserved, set to 0) := '00010000'B
-- Bit 6: - (Reserved, set to 0) := '00100000'B
-- Bit 7: - (Reserved, set to 0) := '01000000'B
-- Bit 8: - (Reserved, set to 0) := '10000000'B

LSAOnlyAccessIndicator ::= ENUMERATED {
	accessOutsideLSAsAllowed (0),
	accessOutsideLSAsRestricted (1)}

LSADataList ::= SEQUENCE SIZE (1..20) OF LSAData

LSAData ::= SEQUENCE {
	lsaIdentity				[0] IMPLICIT LSAIdentity,
	lsaAttributes			[1] IMPLICIT LSAAttributes,
	lsaActiveModeIndicator	[2] IMPLICIT NULL OPTIONAL,
	extensionContainer		[3] IMPLICIT ExtensionContainer OPTIONAL
  }

LSAInformation ::= SEQUENCE {
	completeDataListIncluded	NULL OPTIONAL,
-- If segmentation is used, completeDataListIncluded may only be present in the
-- first segment.
	lsaOnlyAccessIndicator		[1] IMPLICIT LSAOnlyAccessIndicator OPTIONAL,
	lsaDataList					[2] IMPLICIT LSADataList OPTIONAL,
	extensionContainer			[3] IMPLICIT ExtensionContainer OPTIONAL
  }

LSAIdentity ::= OCTET STRING (SIZE (3))
-- Octets are coded according to TS 3GPP TS 23.003 [17]

LSAAttributes ::= OCTET STRING (SIZE (1))
-- Octets are coded according to TS 3GPP TS 48.008 [49]


--   RESULT
InsertSubscriberDataRes ::= SEQUENCE {
	teleserviceList						[1] IMPLICIT TeleserviceList OPTIONAL,
	bearerServiceList					[2] IMPLICIT BearerServiceList OPTIONAL,
	ss-List								[3] IMPLICIT SS-List OPTIONAL,
	odb-GeneralData						[4] IMPLICIT ODB-GeneralData OPTIONAL,
	regionalSubscriptionResponse		[5] IMPLICIT RegionalSubscriptionResponse OPTIONAL,
	supportedCamelPhases				[6] IMPLICIT SupportedCamelPhases OPTIONAL,
	extensionContainer					[7] IMPLICIT ExtensionContainer OPTIONAL,
	offeredCamel4CSIs					[8] IMPLICIT OfferedCamel4CSIs OPTIONAL }

--   ERRORS {
-- dataMissing   localValue : 35, 
-- unexpectedDataValue   localValue : 36, 
-- unidentifiedSubscriber   localValue : 5}
-- ::= localValue : 7

RegionalSubscriptionResponse ::=  ENUMERATED {
            networkNodeAreaRestricted    ( 0 ), 
            tooManyZoneCodes              ( 1 ), 
            zoneCodesConflict             ( 2 ), 
            regionalSubscNotSupported     ( 3 ) 
} 
CallTypeCriteria ::= ENUMERATED {
	forwarded       ( 0 ), 
      notForwarded    ( 1 ) 
}

--deleteSubscriberData OPERATION
--   ARGUMENT

DeleteSubscriberDataArg ::= SEQUENCE {
	imsi											[0] IMPLICIT IMSI,
	basicServiceList								[1] IMPLICIT BasicServiceList OPTIONAL,
-- The exception handling for reception of unsupported/not allocated
-- basicServiceCodes is defined in section 6.8.2
	ss-List											[2] IMPLICIT SS-List OPTIONAL,
	roamingRestrictionDueToUnsupportedFeature		[4] IMPLICIT NULL OPTIONAL,
	regionalSubscriptionIdentifier					[5] IMPLICIT ZoneCode OPTIONAL,
	vbsGroupIndication								[7] IMPLICIT NULL OPTIONAL,
	vgcsGroupIndication								[8] IMPLICIT NULL OPTIONAL,
	camelSubscriptionInfoWithdraw					[9] IMPLICIT NULL OPTIONAL,
	extensionContainer								[6] IMPLICIT ExtensionContainer OPTIONAL,
	gprsSubscriptionDataWithdraw					[10] IMPLICIT GPRSSubscriptionDataWithdraw OPTIONAL,
	roamingRestrictedInSgsnDueToUnsuppportedFeature [11] IMPLICIT NULL OPTIONAL,
	lsaInformationWithdraw							[12] IMPLICIT LSAInformationWithdraw OPTIONAL,
	gmlc-ListWithdraw								[13] IMPLICIT NULL OPTIONAL,
	istInformationWithdraw							[14] NULL OPTIONAL,
	specificCSI-Withdraw							[15] IMPLICIT SpecificCSI-Withdraw OPTIONAL,
	chargingCharacteristicsWithdraw					[16] IMPLICIT NULL OPTIONAL }

--   RESULT
DeleteSubscriberDataRes ::= SEQUENCE {
         regionalSubscriptionResponse   [0] IMPLICIT RegionalSubscriptionResponse OPTIONAL, 
         extensionContainer   ExtensionContainer OPTIONAL
         }
--   ERRORS {
-- dataMissing   localValue : 35, 
-- unexpectedDataValue   localValue : 36, 
-- unidentifiedSubscriber   localValue : 5}
-- ::= localValue : 8

SpecificCSI-Withdraw ::= BIT STRING {
	o-csi (0),
	ss-csi (1),
	tif-csi (2),
	d-csi (3),
	vt-csi (4),
	mo-sms-csi (5),
	m-csi (6),
	gprs-csi (7),
	t-csi (8),
	mt-sms-csi (9),
	mg-csi (10),
	o-IM-CSI (11),
	d-IM-CSI (12),
	vt-IM-CSI (13) } (SIZE(8..32))
-- exception handling:
-- bits 11 to 31 shall be ignored if received by a non-IP Multimedia Core Network entity.
-- bits 0-10 and 14-31 shall be ignored if received by an IP Multimedia Core Network entity.
-- bits 11-13 are only applicable in an IP Multimedia Core Network.
-- Bit 8 and bits 11-13 are only applicable for the NoteSubscriberDataModified operation.

GPRSSubscriptionDataWithdraw ::= CHOICE {
	allGPRSData		NULL,
	contextIdList	ContextIdList}

ContextIdList ::= SEQUENCE SIZE (1..maxNumOfPDP-Contexts) OF
ContextId

LSAInformationWithdraw ::= CHOICE {
	allLSAData			NULL,
	lsaIdentityList		LSAIdentityList }

LSAIdentityList ::= SEQUENCE SIZE (1..maxNumOfLSAs) OF
LSAIdentity


BasicServiceList ::= SEQUENCE SIZE (1..70) OF
Ext-BasicServiceCode

VlrCamelSubscriptionInfo ::= SEQUENCE {
	o-CSI							[0] IMPLICIT O-CSI OPTIONAL,
	extensionContainer				[1] IMPLICIT ExtensionContainer OPTIONAL,
	ss-CSI							[2] IMPLICIT SS-CSI OPTIONAL,
	o-BcsmCamelTDP-CriteriaList		[4] IMPLICIT O-BcsmCamelTDPCriteriaList OPTIONAL,
	tif-CSI							[3] IMPLICIT NULL OPTIONAL,
	m-CSI							[5] IMPLICIT M-CSI OPTIONAL,
	mo-sms-CSI						[6] IMPLICIT SMS-CSI OPTIONAL,
	vt-CSI							[7] IMPLICIT T-CSI OPTIONAL,
	t-BCSM-CAMEL-TDP-CriteriaList	[8] IMPLICIT T-BCSM-CAMEL-TDP-CriteriaList OPTIONAL,
	d-CSI							[9] IMPLICIT D-CSI OPTIONAL,
	mt-sms-CSI						[10] IMPLICIT SMS-CSI OPTIONAL,
	mt-smsCAMELTDP-CriteriaList		[11] IMPLICIT MT-smsCAMELTDP-CriteriaList OPTIONAL
}


MT-smsCAMELTDP-CriteriaList ::= SEQUENCE SIZE (1.. 10) OF
MT-smsCAMELTDP-Criteria

MT-smsCAMELTDP-Criteria ::= SEQUENCE {
	sms-TriggerDetectionPoint	SMS-TriggerDetectionPoint,
	tpdu-TypeCriterion			[0] IMPLICIT TPDU-TypeCriterion OPTIONAL
  }

TPDU-TypeCriterion ::= SEQUENCE SIZE (1..5) OF
MT-SMS-TPDU-Type

MT-SMS-TPDU-Type ::= ENUMERATED {
	sms-DELIVER (0),
	sms-SUBMIT-REPORT (1),
	sms-STATUS-REPORT (2)
  }
-- exception handling:
-- For TPDU-TypeCriterion sequences containing this parameter with any
-- other value than the ones listed above the receiver shall ignore
-- the whole TPDU-TypeCriterion sequence.
-- In CAMEL phase 4, sms-SUBMIT-REPORT shall not be used and a received TPDU-TypeCriterion
-- sequence containing sms-SUBMIT-REPORT shall be wholly ignored.

D-CSI ::= SEQUENCE {
	dp-AnalysedInfoCriteriaList		[0] IMPLICIT DP-AnalysedInfoCriteriaList OPTIONAL,
	camelCapabilityHandling			[1] IMPLICIT CamelCapabilityHandling OPTIONAL,
	extensionContainer				[2] IMPLICIT ExtensionContainer OPTIONAL,
	notificationToCSE				[3] IMPLICIT NULL OPTIONAL,
	csi-Active						[4] IMPLICIT NULL OPTIONAL
  }
-- notificationToCSE and csi-Active shall not be present when D-CSI is sent to VLR/GMSC.
-- They may only be included in ATSI/ATM ack/NSDC message.
-- DP-AnalysedInfoCriteria and camelCapabilityHandling shall be present in
-- the D-CSI sequence.

-- If D-CSI is segmented, then the first segment shall contain dp-AnalysedInfoCriteriaList
-- and camelCapabilityHandling. Subsequent segments shall not contain
-- camelCapabilityHandling, but may contain dp-AnalysedInfoCriteriaList.

DP-AnalysedInfoCriteriaList ::= SEQUENCE SIZE (1..10) OF
DP-AnalysedInfoCriterium

DP-AnalysedInfoCriterium ::= SEQUENCE {
	dialledNumber			ISDN-AddressString,
	serviceKey				ServiceKey,
	gsmSCF-Address			ISDN-AddressString,
	defaultCallHandling		DefaultCallHandling,
	extensionContainer		ExtensionContainer OPTIONAL
  }

SS-CSI ::= SEQUENCE {
	ss-CamelData			SS-CamelData,
	extensionContainer		ExtensionContainer OPTIONAL,
	notificationToCSE		[0] IMPLICIT NULL OPTIONAL,
	csi-Active				[1] IMPLICIT NULL OPTIONAL
-- notificationToCSE and csi-Active shall not be present when SS-CSI is sent to VLR.
-- They may only be included in ATSI/ATM ack/NSDC message.
}

SS-CamelData ::= SEQUENCE {
	ss-EventList			SS-EventList,
	gsmSCF-Address			ISDN-AddressString,
	extensionContainer		[0] IMPLICIT ExtensionContainer OPTIONAL}




MG-CSI ::= SEQUENCE {
	mobilityTriggers		MobilityTriggers,
	serviceKey				ServiceKey,
	gsmSCF-Address			[0] IMPLICIT ISDN-AddressString,
	extensionContainer		[1] IMPLICIT ExtensionContainer OPTIONAL,
	notificationToCSE		[2] IMPLICIT NULL OPTIONAL,
	csi-Active				[3] IMPLICIT NULL OPTIONAL
  }
-- notificationToCSE and csi-Active shall not be present when MG-CSI is sent to SGSN.
-- They may only be included in ATSI/ATM ack/NSDC message.



-- Wireshark adaptation --
Category ::= OCTET STRING (SIZE (1))
-- The internal structure is defined in ITU-T Rec Q.763.

BearerServiceList ::= SEQUENCE SIZE (1..50) OF
Ext-BearerServiceCode

TeleserviceList ::= SEQUENCE SIZE (1..20) OF
Ext-TeleserviceCode


Ext-SS-InfoList ::= SEQUENCE SIZE (1..30) OF
Ext-SS-Info

Ext-SS-Info ::= CHOICE {
	forwardingInfo		[0] IMPLICIT Ext-ForwInfo,
	callBarringInfo		[1] IMPLICIT Ext-CallBarInfo,
	cug-Info			[2] IMPLICIT CUG-Info,
	ss-Data				[3] IMPLICIT Ext-SS-Data,
	emlpp-Info			[4] IMPLICIT EMLPP-Info}

Ext-ForwInfo ::= SEQUENCE {
	ss-Code					SS-Code,
	forwardingFeatureList	Ext-ForwFeatureList,
	extensionContainer		[0] IMPLICIT ExtensionContainer OPTIONAL
  }

Ext-ForwFeatureList ::= SEQUENCE SIZE (1..maxNumOfExt-BasicServiceGroups) OF Ext-ForwFeature

Ext-ForwFeature ::= SEQUENCE {
	basicService			Ext-BasicServiceCode OPTIONAL,
	ss-Status				[4] IMPLICIT Ext-SS-Status,
	forwardedToNumber		[5] IMPLICIT ISDN-AddressString OPTIONAL,
-- When this data type is sent from an HLR which supports CAMEL Phase 2
-- to a VLR that supports CAMEL Phase 2 the VLR shall not check the
-- format of the number
	forwardedToSubaddress	[8] IMPLICIT ISDN-SubaddressString OPTIONAL,
	forwardingOptions		[6] IMPLICIT Ext-ForwOptions OPTIONAL,
	noReplyConditionTime	[7] IMPLICIT Ext-NoRepCondTime OPTIONAL,
	extensionContainer		[9] IMPLICIT ExtensionContainer OPTIONAL,
	longForwardedToNumber	[10] IMPLICIT FTN-AddressString OPTIONAL }

Ext-ForwOptions ::= OCTET STRING (SIZE (1..5))
-- OCTET 1:
-- bit 8: notification to forwarding party
-- 0 no notification
-- 1 notification
-- bit 7: redirecting presentation
-- 0 no presentation
-- 1 presentation
-- bit 6: notification to calling party
-- 0 no notification
-- 1 notification
-- bit 5: 0 (unused)
-- bits 43: forwarding reason
-- 00 ms not reachable
-- 01 ms busy
-- 10 no reply
-- 11 unconditional
-- bits 21: 00 (unused)
-- OCTETS 2-5: reserved for future use. They shall be discarded if
-- received and not understood.

Ext-NoRepCondTime ::= INTEGER (1..100)
-- Only values 5-30 are used.
-- Values in the ranges 1-4 and 31-100 are reserved for future use
-- If received:
-- values 1-4 shall be mapped on to value 5
-- values 31-100 shall be mapped on to value 30

Ext-CallBarInfo ::= SEQUENCE {
	ss-Code					SS-Code,
	callBarringFeatureList	Ext-CallBarFeatureList,
	extensionContainer		ExtensionContainer OPTIONAL
  }

Ext-CallBarFeatureList ::= SEQUENCE SIZE (1..maxNumOfExt-BasicServiceGroups) OF
Ext-CallBarringFeature

Ext-CallBarringFeature ::= SEQUENCE {
	basicService		Ext-BasicServiceCode OPTIONAL,
	ss-Status			[4] IMPLICIT Ext-SS-Status,
	extensionContainer	ExtensionContainer OPTIONAL
  }

ZoneCodeList ::= SEQUENCE SIZE (1..10)
OF ZoneCode

ZoneCode ::= OCTET STRING (SIZE (2))
-- internal structure is defined in TS 3GPP TS 23.003 [17]


EMLPP-Info ::= SEQUENCE {
	maximumentitledPriority		EMLPP-Priority,
	defaultPriority				EMLPP-Priority,
	extensionContainer			ExtensionContainer OPTIONAL
  }

EMLPP-Priority ::= INTEGER (0..15)
-- The mapping from the values A,B,0,1,2,3,4 to the integer-value is
-- specified as follows where A is the highest and 4 is the lowest
-- priority level
-- the integer values 7-15 are spare and shall be mapped to value 4

CliRestrictionOption ::= ENUMERATED {
                  permanent                     ( 0 ), 
                  temporaryDefaultRestricted    ( 1 ), 
                  temporaryDefaultAllowed       ( 2 ) 
}


SS-Status ::= OCTET STRING ( SIZE( 1 .. 5 ) )

CUG-Info ::= SEQUENCE {
	cug-SubscriptionList	CUG-SubscriptionList,
	cug-FeatureList			CUG-FeatureList OPTIONAL,
	extensionContainer		[0] IMPLICIT ExtensionContainer OPTIONAL
  }

CUG-SubscriptionList ::= SEQUENCE SIZE (0..10) OF
CUG-Subscription

CUG-Subscription ::= SEQUENCE {
	cug-Index				CUG-Index,
	cug-Interlock			CUG-Interlock,
	intraCUG-Options		IntraCUG-Options,
	basicServiceGroupList	Ext-BasicServiceGroupList OPTIONAL,
	extensionContainer		[0] IMPLICIT ExtensionContainer OPTIONAL
  }

CUG-Index ::= INTEGER (0..32767)
-- The internal structure is defined in ETS 300 138.

CUG-Interlock ::= OCTET STRING (SIZE (4))

IntraCUG-Options ::= ENUMERATED {
	noCUG-Restrictions (0),
	cugIC-CallBarred (1),
	cugOG-CallBarred (2)}

CUG-FeatureList ::= SEQUENCE SIZE (1..32) OF
CUG-Feature

Ext-BasicServiceGroupList ::= SEQUENCE SIZE (1..32) OF
Ext-BasicServiceCode

CUG-Feature ::= SEQUENCE {
	basicService				Ext-BasicServiceCode OPTIONAL,
	preferentialCUG-Indicator	CUG-Index OPTIONAL,
	interCUG-Restrictions		InterCUG-Restrictions,
	extensionContainer			ExtensionContainer OPTIONAL
  }

InterCUG-Restrictions ::= OCTET STRING (SIZE (1))
-- bits 876543: 000000 (unused)
-- Exception handling:
-- bits 876543 shall be ignored if received and not understood
-- bits 21
-- 00 CUG only facilities
-- 01 CUG with outgoing access
-- 10 CUG with incoming access
-- 11 CUG with both outgoing and incoming access

Ext-SS-Data ::= SEQUENCE {
	ss-Code					SS-Code,
	ss-Status				[4] IMPLICIT Ext-SS-Status,
	ss-SubscriptionOption	SS-SubscriptionOption OPTIONAL,
	basicServiceGroupList	Ext-BasicServiceGroupList OPTIONAL,
	extensionContainer		[5] IMPLICIT ExtensionContainer OPTIONAL
  }

LCS-PrivacyExceptionList ::= SEQUENCE SIZE (1..4) OF
LCS-PrivacyClass

LCS-PrivacyClass ::= SEQUENCE {
	ss-Code							SS-Code,
	ss-Status						Ext-SS-Status,
	notificationToMSUser			[0] IMPLICIT NotificationToMSUser OPTIONAL,
--
-- notificationToMSUser may be sent only for SS-codes callSessionRelated
-- and callSessionUnrelated. If not received for SS-codes callSessionRelated
-- and callSessionUnrelated,
-- the default values according to 3GPP TS 23.271 shall be assumed.
--
	externalClientList				[1] IMPLICIT ExternalClientList OPTIONAL,
--
-- externalClientList may be sent only for SS-code callSessionUnrelated to a
-- visited node that does not support LCS Release 4 or later versions.
-- externalClientList may be sent only for SS-codes callSessionUnrelated and
-- callSessionRelated to a visited node that supports LCS Release 4 or later versions.
--
	plmnClientList					[2] IMPLICIT PLMNClientList OPTIONAL,
--
-- plmnClientList may be sent only for SS-code plmnoperator.
	extensionContainer				[3] IMPLICIT ExtensionContainer OPTIONAL,
	ext-externalClientList			[4] IMPLICIT Ext-ExternalClientList OPTIONAL,
-- Ext-externalClientList may be sent only if the visited node supports LCS Release 4 or
-- later versions, the user did specify more than 5 clients, and White Book SCCP is used.
--
	serviceTypeList					[5] IMPLICIT ServiceTypeList OPTIONAL
--
-- serviceTypeList may be sent only for SS-code serviceType and if the visited node
-- supports LCS Release 5 or later versions.
--
-- if segmentation is used, the complete LCS-PrivacyClass shall be sent in one segment
}

ExternalClientList ::= SEQUENCE SIZE (0..5) OF
ExternalClient

PLMNClientList ::= SEQUENCE SIZE (1..5) OF
LCSClientInternalID

Ext-ExternalClientList ::= SEQUENCE SIZE (1..35) OF
ExternalClient

ExternalClient ::= SEQUENCE {
	clientIdentity			LCSClientExternalID,
	gmlc-Restriction		[0] IMPLICIT GMLC-Restriction OPTIONAL,
	notificationToMSUser	[1] IMPLICIT NotificationToMSUser OPTIONAL,
-- If notificationToMSUser is not received, the default value according to
-- 3GPP TS 23.271 shall be assumed.
	extensionContainer		[2] IMPLICIT ExtensionContainer OPTIONAL
  }

GMLC-Restriction ::= ENUMERATED {
	gmlc-List (0),
	home-Country (1)
  }
-- exception handling:
-- At reception of any other value than the ones listed the receiver shall ignore
-- GMLC-Restriction.

NotificationToMSUser ::= ENUMERATED {
	notifyLocationAllowed (0),
	notifyAndVerify-LocationAllowedIfNoResponse (1),
	notifyAndVerify-LocationNotAllowedIfNoResponse (2),
	locationNotAllowed (3) }
-- exception handling:
-- At reception of any other value than the ones listed the receiver shall ignore
-- NotificationToMSUser.


ServiceTypeList ::= SEQUENCE SIZE (1..32) OF
ServiceType

ServiceType ::= SEQUENCE {
	serviceTypeIdentity			LCSServiceTypeID,
	gmlc-Restriction			[0] IMPLICIT GMLC-Restriction OPTIONAL,
	notificationToMSUser		[1] IMPLICIT NotificationToMSUser OPTIONAL,
-- If notificationToMSUser is not received, the default value according to
-- 3GPP TS 23.271 shall be assumed.
	extensionContainer			[2] IMPLICIT ExtensionContainer OPTIONAL
	}

MOLR-List ::= SEQUENCE SIZE (1..3) OF
MOLR-Class

MOLR-Class ::= SEQUENCE {
	ss-Code					SS-Code,
	ss-Status				Ext-SS-Status,
	extensionContainer		[0] IMPLICIT ExtensionContainer OPTIONAL
  }

CallBarringFeatureList ::= SEQUENCE SIZE (1..32) OF CallBarringFeature

CallBarringFeature ::= SEQUENCE {
	basicService	BasicServiceCode OPTIONAL,
	ss-Status		[4] IMPLICIT SS-Status OPTIONAL
  }

ForwardingFeatureList ::= SEQUENCE SIZE (1..maxNumOfBasicServiceGroups) OF ForwardingFeature

ForwardingFeature ::= SEQUENCE {
	basicService					BasicServiceCode OPTIONAL,
	ss-Status						[4] IMPLICIT SS-Status OPTIONAL,
	forwardedToNumber				[5] IMPLICIT ISDN-AddressString OPTIONAL,
	forwardedToSubaddress			[8] IMPLICIT ISDN-SubaddressString OPTIONAL,
	forwardingOptions				[6] IMPLICIT ForwardingOptions OPTIONAL,
	noReplyConditionTime			[7] IMPLICIT NoReplyConditionTime OPTIONAL,
	longForwardedToNumber			[9] IMPLICIT FTN-AddressString OPTIONAL }

LongForwardedToNumber ::= OCTET STRING (  SIZE (1 .. 20 ) ) 


DestinationNumberCriteria ::= SEQUENCE {
	matchType						[0] IMPLICIT MatchType,
	destinationNumberList			[1] IMPLICIT DestinationNumberList OPTIONAL,
	destinationNumberLengthList		[2] IMPLICIT DestinationNumberLengthList OPTIONAL
-- one or both of destinationNumberList and destinationNumberLengthList
-- shall be present
  }


DestinationNumberList ::= SEQUENCE SIZE (1..10) OF
ISDN-AddressString
-- The receiving entity shall not check the format of a number in
-- the dialled number list

DestinationNumberLengthList ::= SEQUENCE SIZE (1..3) OF
INTEGER(1..15)

ForwardingInfo ::= SEQUENCE {
	ss-Code					SS-Code OPTIONAL,
	forwardingFeatureList	ForwardingFeatureList
  }

ForwardingOptions ::= OCTET STRING ( SIZE( 1 ) )
-- bit 8: notification to forwarding party
-- 0 no notification
-- 1 notification
-- bit 7: redirecting presentation
-- 0 no presentation
-- 1 presentation
-- bit 6: notification to calling party
-- 0 no notification
-- 1 notification
-- bit 5: 0 (unused)
-- bits 43: forwarding reason
-- 00 ms not reachable
-- 01 ms busy
-- 10 no reply
-- 11 unconditional when used in a SRI Result,
-- or call deflection when used in a RCH Argument
-- bits 21: 00 (unused)

CallBarringInfo ::= SEQUENCE {
	ss-Code					SS-Code OPTIONAL,
	callBarringFeatureList	CallBarringFeatureList
  }

--  noReplyConditionTime    [7] IMPLICIT INTEGER ( 1 .. 100 ) OPTIONAL, 
-- Changed to no size


MC-SS-Info ::= SEQUENCE {
	ss-Code				[0] IMPLICIT SS-Code,
	ss-Status			[1] IMPLICIT Ext-SS-Status,
	nbrSB				[2] IMPLICIT MaxMC-Bearers,
	nbrUser				[3] IMPLICIT MC-Bearers,
	extensionContainer	[4] IMPLICIT ExtensionContainer OPTIONAL
  }

MaxMC-Bearers ::= INTEGER (2..7)

MC-Bearers ::= INTEGER (1..7)


--reset      OPERATION
--   ARGUMENT
ResetArg ::= SEQUENCE {
	hlr-Number	ISDN-AddressString,
	hlr-List	HLR-List OPTIONAL
  }

-- ::= localValue : 37
Hlr-Number ::= OCTET STRING ( SIZE( 1 .. 20 ) ) ( SIZE( 1 .. 9 ) )
--forwardCheckSS-Indication OPERATION
-- ::= localValue : 38

--restoreData OPERATION
--   ARGUMENT
RestoreDataArg ::= SEQUENCE {
         imsi                 IMSI, 
         lmsi                 LMSI OPTIONAL, 
         extensionContainer   ExtensionContainer OPTIONAL, 
         vlr-Capability       [6] IMPLICIT VLR-Capability OPTIONAL}
--   RESULT
RestoreDataRes ::= SEQUENCE {
         hlr-Number           ISDN-AddressString, 
         msNotReachable       NULL OPTIONAL, 
         extensionContainer   ExtensionContainer OPTIONAL
         }
--   ERRORS {
-- systemFailure   localValue : 34, 
-- dataMissing   localValue : 35, 
-- unexpectedDataValue   localValue : 36, 
-- unknownSubscriber   localValue : 1}
-- ::= localValue : 57

VBSDataList ::= SEQUENCE SIZE (1..50) OF VoiceBroadcastData
VGCSDataList ::= SEQUENCE SIZE (1..50) OF VoiceGroupCallData

VoiceGroupCallData ::= SEQUENCE {
	groupId				GroupId,
	extensionContainer	ExtensionContainer OPTIONAL
  }

VoiceBroadcastData ::= SEQUENCE {
	groupid						GroupId,
	broadcastInitEntitlement	NULL OPTIONAL,
	extensionContainer			ExtensionContainer OPTIONAL
  }

GroupId ::= TBCD-STRING (SIZE (3))
-- When Group-Id is less than six characters in length, the TBCD filler (1111)
-- is used to fill unused half octets.
-- Refers to the Group Identification as specified in 3GPP TS 23.003
-- and 3GPP TS 43.068/ 43.069

--activateTraceMode OPERATION
--   ARGUMENT
ActivateTraceModeArg ::= SEQUENCE {
         imsi                 [0] IMPLICIT IMSI OPTIONAL, 
         traceReference       [1] IMPLICIT OCTET STRING ( SIZE( 1 .. 2 ) ), 
         traceType            [2] IMPLICIT INTEGER ( 0 .. 255 ), 
         omc-Id               [3] IMPLICIT OCTET STRING ( SIZE( 1 .. 20 ) ) OPTIONAL, 
         extensionContainer   [4] IMPLICIT ExtensionContainer OPTIONAL
         }
--   RESULT
ActivateTraceModeRes ::= SEQUENCE {
         extensionContainer   [0] IMPLICIT ExtensionContainer OPTIONAL
         }
--   ERRORS {
-- systemFailure   localValue : 34, 
-- dataMissing   localValue : 35, 
-- unexpectedDataValue   localValue : 36, 
-- facilityNotSupported   localValue : 21, 
-- unidentifiedSubscriber   localValue : 5, 
-- tracingBufferFull   localValue : 40}
-- ::= localValue : 50

--deactivateTraceMode OPERATION
--   ARGUMENT
DeactivateTraceModeArg ::= SEQUENCE {
         imsi                 [0] IMPLICIT IMSI OPTIONAL, 
         traceReference       [1] IMPLICIT OCTET STRING ( SIZE( 1 .. 2 ) ), 
         extensionContainer   [2] IMPLICIT ExtensionContainer OPTIONAL
         }
--   RESULT
DeactivateTraceModeRes ::= SEQUENCE {
         extensionContainer   [0] IMPLICIT ExtensionContainer OPTIONAL
         }
--   ERRORS {
-- systemFailure   localValue : 34, 
-- dataMissing   localValue : 35, 
-- unexpectedDataValue   localValue : 36, 
-- facilityNotSupported   localValue : 21, 
-- unidentifiedSubscriber   localValue : 5}
-- ::= localValue : 51

--sendIMSI   OPERATION
--   ARGUMENT
--Msisdn ::=defined elsewhere
--   RESULT
--IMSI ::= defined elsewhere
--   ERRORS {
-- dataMissing   localValue : 35, 
-- unexpectedDataValue   localValue : 36, 
-- unknownSubscriber   localValue : 1}
-- ::= localValue : 58

--sendRoutingInfo OPERATION
--   ARGUMENT

SendRoutingInfoArg ::= SEQUENCE {
	msisdn							[0] IMPLICIT ISDN-AddressString,
	cug-CheckInfo					[1] IMPLICIT CUG-CheckInfo OPTIONAL,
	numberOfForwarding				[2] IMPLICIT NumberOfForwarding OPTIONAL,
	interrogationType				[3] IMPLICIT InterrogationType,
	or-Interrogation				[4] IMPLICIT NULL OPTIONAL,
	or-Capability					[5] IMPLICIT OR-Phase OPTIONAL,
	gmsc-OrGsmSCF-Address			[6] IMPLICIT ISDN-AddressString,
	callReferenceNumber				[7] IMPLICIT CallReferenceNumber OPTIONAL,
	forwardingReason				[8] IMPLICIT ForwardingReason OPTIONAL,
	basicServiceGroup				[9] IMPLICIT Ext-BasicServiceCode OPTIONAL,
	networkSignalInfo				[10] IMPLICIT ExternalSignalInfo OPTIONAL,
	camelInfo						[11] IMPLICIT CamelInfo OPTIONAL,
	suppressionOfAnnouncement		[12] IMPLICIT SuppressionOfAnnouncement OPTIONAL,
	extensionContainer				[13] IMPLICIT ExtensionContainer OPTIONAL,
	alertingPattern					[14] IMPLICIT AlertingPattern OPTIONAL,
	ccbs-Call						[15] IMPLICIT NULL OPTIONAL,
	supportedCCBS-Phase				[16] IMPLICIT SupportedCCBS-Phase OPTIONAL,
	additionalSignalInfo			[17] IMPLICIT Ext-ExternalSignalInfo OPTIONAL,
	istSupportIndicator				[18] IMPLICIT IST-SupportIndicator OPTIONAL,
	pre-pagingSupported				[19] IMPLICIT NULL OPTIONAL,
	callDiversionTreatmentIndicator [20] IMPLICIT CallDiversionTreatmentIndicator OPTIONAL,
	longFTN-Supported				[21] IMPLICIT NULL OPTIONAL,
	suppress-VT-CSI					[22] NULL OPTIONAL,
	suppressIncomingCallBarring		[23] NULL OPTIONAL,
	gsmSCF-InitiatedCall			[24] NULL OPTIONAL,
	basicServiceGroup2				[25] IMPLICIT Ext-BasicServiceCode OPTIONAL,
	networkSignalInfo2				[26] IMPLICIT ExternalSignalInfo OPTIONAL
}
--   RESULT
SendRoutingInfoRes ::= [3] SEQUENCE {
	imsi							[9] IMPLICIT IMSI OPTIONAL,
	-- IMSI must be present if SendRoutingInfoRes is not segmented.
	-- If the TC-Result-NL segmentation option is taken the IMSI must be
	-- present in one segmented transmission of SendRoutingInfoRes.
	extendedRoutingInfo				ExtendedRoutingInfo OPTIONAL,
	cug-CheckInfo					[3] IMPLICIT CUG-CheckInfo OPTIONAL,
	cugSubscriptionFlag				[6] IMPLICIT NULL OPTIONAL,
	subscriberInfo					[7] IMPLICIT SubscriberInfo OPTIONAL,
	ss-List							[1] IMPLICIT SS-List OPTIONAL,
	basicService					[5] IMPLICIT Ext-BasicServiceCode OPTIONAL,
	forwardingInterrogationRequired [4] IMPLICIT NULL OPTIONAL,
	vmsc-Address					[2] IMPLICIT ISDN-AddressString OPTIONAL,
	extensionContainer				[0] IMPLICIT ExtensionContainer OPTIONAL,
	naea-PreferredCI				[10] IMPLICIT NAEA-PreferredCI OPTIONAL,
	-- naea-PreferredCI is included at the discretion of the HLR operator.
	ccbs-Indicators					[11] IMPLICIT CCBS-Indicators OPTIONAL,
	msisdn							[12] IMPLICIT ISDN-AddressString OPTIONAL,
	numberPortabilityStatus			[13] IMPLICIT NumberPortabilityStatus OPTIONAL,
	istAlertTimer					[14] IMPLICIT IST-AlertTimerValue OPTIONAL,
	supportedCamelPhasesInVMSC		[15] IMPLICIT SupportedCamelPhases OPTIONAL,
	offeredCamel4CSIsInVMSC			[16] IMPLICIT OfferedCamel4CSIs OPTIONAL,
	routingInfo2					[17] IMPLICIT RoutingInfo OPTIONAL,
	ss-List2						[18] IMPLICIT SS-List OPTIONAL,
	basicService2					[19] IMPLICIT Ext-BasicServiceCode OPTIONAL,
	allowedServices					[20] IMPLICIT AllowedServices OPTIONAL,
	unavailabilityCause				[21] IMPLICIT UnavailabilityCause OPTIONAL,
	releaseResourcesSupported		[22] IMPLICIT NULL OPTIONAL
}
--   ERRORS {
-- systemFailure   localValue : 34, 
-- dataMissing   localValue : 35, 
-- unexpectedDataValue   localValue : 36, 
-- facilityNotSupported   localValue : 21, 
-- or-NotAllowed   localValue : 48, 
-- unknownSubscriber   localValue : 1, 
-- numberChanged   localValue : 44, 
-- bearerServiceNotProvisioned   localValue : 10, 
-- teleserviceNotProvisioned   localValue : 11, 
-- absentSubscriber   localValue : 27, 
-- busySubscriber   localValue : 45, 
-- noSubscriberReply   localValue : 46, 
-- callBarred   localValue : 13, 
-- cug-Reject   localValue : 15, 
-- forwardingViolation   localValue : 14}
-- ::= localValue : 22

NumberOfForwarding ::= INTEGER (1..5)

InterrogationType ::= ENUMERATED {
	basicCall (0),
	forwarding (1)}

OR-Phase ::= INTEGER (1..127)

CallReferenceNumber ::= OCTET STRING (SIZE (1..8))

ForwardingReason ::= ENUMERATED {
	notReachable (0),
	busy (1),
	noReply (2)}

ExternalSignalInfo ::= SEQUENCE {
	protocolId			ProtocolId,
	signalInfo			SignalInfo,
-- Information about the internal structure is given in
-- clause 7.6.9.
	extensionContainer	ExtensionContainer OPTIONAL
-- extensionContainer must not be used in version 2
  }

SignalInfo ::= OCTET STRING (SIZE (1..200))

Ext-ExternalSignalInfo ::= SEQUENCE {
	ext-ProtocolId		Ext-ProtocolId,
	signalInfo			SignalInfo,
-- Information about the internal structure is given in
-- clause 7.6.9.10
	extensionContainer	ExtensionContainer OPTIONAL
  }

Ext-ProtocolId ::= ENUMERATED {
	ets-300356 (1)
}

AccessNetworkSignalInfo ::= SEQUENCE {
	accessNetworkProtocolId		AccessNetworkProtocolId,
	signalInfo					LongSignalInfo,
-- Information about the internal structure is given in clause 7.6.9.1
	extensionContainer			ExtensionContainer OPTIONAL
  }

LongSignalInfo ::= OCTET STRING (SIZE (1..2560))

CamelInfo ::= SEQUENCE {
	supportedCamelPhases	SupportedCamelPhases,
	suppress-T-CSI			NULL OPTIONAL,
	extensionContainer		ExtensionContainer OPTIONAL,
	offeredCamel4CSIs		[0] IMPLICIT OfferedCamel4CSIs OPTIONAL }

-- exception handling:
-- For Ext-ExternalSignalInfo sequences containing this parameter with any
-- other value than the ones listed the receiver shall ignore the whole
-- Ext-ExternalSignalInfo sequence.

SuppressionOfAnnouncement ::= NULL

AccessNetworkProtocolId ::= ENUMERATED {
	ts3G-48006 (1),
	ts3G-25413 (2)
  }

-- exception handling:
-- For AccessNetworkSignalInfo sequences containing this parameter with any
-- other value than the ones listed the receiver shall ignore the whole
-- AccessNetworkSignalInfo sequence.

AlertingPattern ::= OCTET STRING (SIZE (1) )
-- This type is used to represent Alerting Pattern
-- bits 8765 : 0000 (unused)
-- bits 43 : type of Pattern
-- 00 level
-- 01 category
-- 10 category
-- all other values are reserved.
-- bits 21 : type of alerting

IMSI ::= OCTET STRING (SIZE (3..8))
-- digits of MCC, MNC, MSIN are concatenated in this order.

TBCD-STRING ::= OCTET STRING
-- This type (Telephony Binary Coded Decimal String) is used to
-- represent several digits from 0 through 9, *, #, a, b, c, two
-- digits per octet, each digit encoded 0000 to 1001 (0 to 9),
-- 1010 (*), 1011 (#), 1100 (a), 1101 (b) or 1110 (c); 1111 used
-- as filler when there is an odd number of digits.
-- bits 8765 of octet n encoding digit 2n
-- bits 4321 of octet n encoding digit 2(n-1) +1


LMSI ::= OCTET STRING ( SIZE( 4 ) )


Identity ::= CHOICE {
	imsi			IMSI,
	imsi-WithLMSI	IMSI-WithLMSI}

IMSI-WithLMSI ::= SEQUENCE {
	imsi	IMSI,
	lmsi	LMSI
-- a special value 00000000 indicates that the LMSI is not in use
  }

ASCI-CallReference ::= TBCD-STRING (SIZE (1..8))
-- digits of VGCS/VBC-area,Group-ID are concatenated in this order.

TMSI ::= OCTET STRING (SIZE (1..4))

SubscriberId ::= CHOICE {
	imsi [0] IMSI,
	tmsi [1] TMSI}

IMEI ::= TBCD-STRING (SIZE (8))

-- Refers to International Mobile Station Equipment Identity
-- and Software Version Number (SVN) defined in TS 3GPP TS 23.003 [17].
-- If the SVN is not present the last octet shall contain the
-- digit 0 and a filler.
-- If present the SVN shall be included in the last octet.

HLR-Id ::= IMSI
-- leading digits of IMSI, i.e. (MCC, MNC, leading digits of
-- MSIN) forming HLR Id defined in TS 3GPP TS 23.003 [17].

HLR-List ::= SEQUENCE SIZE (1..50) OF HLR-Id


SupportedCCBS-Phase ::= INTEGER (1..127)
-- exception handling:
-- Only value 1 is used.
-- Values in the ranges 2-127 are reserved for future use.
-- If received values 2-127 shall be mapped on to value 1.

CallDiversionTreatmentIndicator ::= OCTET STRING (SIZE(1))
-- callDiversionAllowed (xxxx xx01)
-- callDiversionNotAllowed (xxxx xx10)
-- network default is call diversion allowed


SS-List ::= SEQUENCE SIZE (1..30) OF
SS-Code

NAEA-PreferredCI ::= SEQUENCE {
	naea-PreferredCIC	[0] IMPLICIT NAEA-CIC,
	extensionContainer	[1] IMPLICIT ExtensionContainer OPTIONAL
  }

NAEA-CIC ::= OCTET STRING (SIZE (3))
-- The internal structure is defined by the Carrier Identification
-- parameter in ANSI T1.113.3. Carrier codes between '000' and '999' may
-- be encoded as 3 digits using '000' to '999' or as 4 digits using
-- '0000' to '0999'. Carrier codes between '1000' and '9999' are encoded
-- using 4 digits.

SubscriberIdentity ::= CHOICE {
            imsi         [0] IMPLICIT IMSI, 
            msisdn       [1] IMPLICIT ISDN-AddressString
			}

LCSClientExternalID ::= SEQUENCE {
	externalAddress			[0] IMPLICIT ISDN-AddressString OPTIONAL,
	extensionContainer		[1] IMPLICIT ExtensionContainer OPTIONAL
  }

LCSClientInternalID ::= ENUMERATED {
	broadcastService (0),
	o-andM-HPLMN (1),
	o-andM-VPLMN (2),
	anonymousLocation (3),
	targetMSsubscribedService (4)
  }
-- for a CAMEL phase 3 PLMN operator client, the value targetMSsubscribedService shall be used

LCSServiceTypeID ::= INTEGER (0..127)
-- the integer values 0-63 are reserved for Standard LCS service types
-- the integer values 64-127 are reserved for Non Standard LCS service types

CellGlobalIdOrServiceAreaIdOrLAI ::= CHOICE {
	cellGlobalIdOrServiceAreaIdFixedLength	[0] IMPLICIT CellGlobalIdOrServiceAreaIdFixedLength,
	laiFixedLength							[1] IMPLICIT LAIFixedLength}

CellGlobalIdOrServiceAreaIdFixedLength ::= OCTET STRING (SIZE (7))
-- Refers to Cell Global Identification or Service Area Identification
-- defined in 3GPP TS 23.003.
-- The internal structure is defined as follows:
-- octet 1 bits 4321 Mobile Country Code 1st digit
-- bits 8765 Mobile Country Code 2nd digit
-- octet 2 bits 4321 Mobile Country Code 3rd digit
-- bits 8765 Mobile Network Code 3rd digit
-- or filler (1111) for 2 digit MNCs
-- octet 3 bits 4321 Mobile Network Code 1st digit
-- bits 8765 Mobile Network Code 2nd digit
-- octets 4 and 5 Location Area Code according to 3GPP TS 24.008
-- octets 6 and 7 Cell Identity (CI) value or
-- Service Area Code (SAC) value
-- according to 3GPP TS 23.003

LAIFixedLength ::= OCTET STRING (SIZE (5))
-- Refers to Location Area Identification defined in TS 3GPP TS 23.003 [17].
-- The internal structure is defined as follows:
-- octet 1 bits 4321 Mobile Country Code 1st digit
-- bits 8765 Mobile Country Code 2nd digit
-- octet 2 bits 4321 Mobile Country Code 3rd digit
-- bits 8765 Mobile Network Code 3rd digit
-- or filler (1111) for 2 digit MNCs
-- octet 3 bits 4321 Mobile Network Code 1st digit
-- bits 8765 Mobile Network Code 2nd digit
-- octets 4 and 5 Location Area Code according to TS 3GPP TS 24.008[35]

AllowedServices ::= BIT STRING {
	firstServiceAllowed (0),
	secondServiceAllowed (1) } (SIZE (2..8))
-- firstService is the service indicated in the networkSignalInfo
-- secondService is the service indicated in the networkSignalInfo2
-- Other bits than listed above shall be discarded

UnavailabilityCause ::= ENUMERATED {
	bearerServiceNotProvisioned (1),
	teleserviceNotProvisioned (2),
	absentSubscriber (3),
	busySubscriber (4),
	callBarred (5),
	cug-Reject (6)
  }
-- exception handling:
-- Reception of other values than the ones listed shall result in the service
-- being unavailable for that call.

CCBS-Indicators ::= SEQUENCE {
	ccbs-Possible			[0] IMPLICIT NULL OPTIONAL,
	keepCCBS-CallIndicator	[1] IMPLICIT NULL OPTIONAL,
	extensionContainer		[2] IMPLICIT ExtensionContainer OPTIONAL
  }

RoutingInfo ::= CHOICE {
	roamingNumber ISDN-AddressString,
	forwardingData ForwardingData}

ExtendedRoutingInfo ::= CHOICE {
	routingInfo			RoutingInfo,
	camelRoutingInfo	[8] IMPLICIT CamelRoutingInfo}

CamelRoutingInfo ::= SEQUENCE {
	forwardingData					ForwardingData OPTIONAL,
	gmscCamelSubscriptionInfo		[0] IMPLICIT GmscCamelSubscriptionInfo,
	extensionContainer				[1] IMPLICIT ExtensionContainer OPTIONAL
  }

GmscCamelSubscriptionInfo ::= SEQUENCE {
	t-CSI							[0] IMPLICIT T-CSI OPTIONAL,
	o-CSI							[1] IMPLICIT O-CSI OPTIONAL,
	extensionContainer				[2] IMPLICIT ExtensionContainer OPTIONAL,
	o-BcsmCamelTDP-CriteriaList		[3] IMPLICIT O-BcsmCamelTDPCriteriaList OPTIONAL,
	t-BCSM-CAMEL-TDP-CriteriaList	[4] IMPLICIT T-BCSM-CAMEL-TDP-CriteriaList OPTIONAL,
	d-csi							[5] IMPLICIT D-CSI OPTIONAL}


MatchType ::= ENUMERATED {
              inhibiting    ( 0 ), 
              enabling      ( 1 ) 
}


LocationInformation ::= SEQUENCE {
	ageOfLocationInformation				AgeOfLocationInformation OPTIONAL,
	geographicalInformation					[0] IMPLICIT GeographicalInformation OPTIONAL,
	vlr-number								[1] IMPLICIT ISDN-AddressString OPTIONAL,
	locationNumber							[2] IMPLICIT LocationNumber OPTIONAL,
	cellGlobalIdOrServiceAreaIdOrLAI		[3] IMPLICIT CellGlobalIdOrServiceAreaIdOrLAI OPTIONAL,
	extensionContainer						[4] IMPLICIT ExtensionContainer OPTIONAL,
	selectedLSA-Id							[5] IMPLICIT LSAIdentity OPTIONAL,
	msc-Number								[6] IMPLICIT ISDN-AddressString OPTIONAL,
	geodeticInformation						[7] IMPLICIT GeodeticInformation OPTIONAL,
	currentLocationRetrieved				[8] IMPLICIT NULL OPTIONAL,
	sai-Present								[9] IMPLICIT NULL OPTIONAL }
-- sai-Present indicates that the cellGlobalIdOrServiceAreaIdOrLAI parameter contains
-- a Service Area Identity.
-- currentLocationRetrieved shall be present
-- if the location information were retrieved after a successfull paging.

LocationInformationGPRS ::= SEQUENCE {
	cellGlobalIdOrServiceAreaIdOrLAI		[0] CellGlobalIdOrServiceAreaIdOrLAI OPTIONAL,
	routeingAreaIdentity					[1] RAIdentity OPTIONAL,
	geographicalInformation					[2] GeographicalInformation OPTIONAL,
	sgsn-Number								[3] ISDN-AddressString OPTIONAL,
	selectedLSAIdentity						[4] LSAIdentity OPTIONAL,
	extensionContainer						[5] ExtensionContainer OPTIONAL,
	sai-Present								[6] NULL OPTIONAL,
	geodeticInformation						[7] GeodeticInformation OPTIONAL,
	currentLocationRetrieved				[8] NULL OPTIONAL,
	ageOfLocationInformation				[9] AgeOfLocationInformation OPTIONAL }
-- sai-Present indicates that the cellGlobalIdOrServiceAreaIdOrLAI parameter contains
-- a Service Area Identity.
-- currentLocationRetrieved shall be present if the location information
-- was retrieved after successful paging.

RAIdentity ::= OCTET STRING (SIZE (6))
-- Routing Area Identity is coded in accordance with 3GPP TS 29.060 [105].
-- It shall contain the value part defined in 3GPP TS 29.060 only. I.e. the 3GPP TS 29.060
-- type identifier octet shall not be included.

GeographicalInformation ::= OCTET STRING (SIZE (8))
-- Refers to geographical Information defined in 3GPP TS 23.032.
-- Only the description of an ellipsoid point with uncertainty circle
-- as specified in 3GPP TS 23.032 is allowed to be used
-- The internal structure according to 3GPP TS 23.032 is as follows:
-- Type of shape (ellipsoid point with uncertainty circle) 1 octet
-- Degrees of Latitude 3 octets
-- Degrees of Longitude 3 octets
-- Uncertainty code 1 octet

GeodeticInformation ::= OCTET STRING (SIZE (10))
-- Refers to Calling Geodetic Location defined in Q.763 (1999).
-- Only the description of an ellipsoid point with uncertainty circle
-- as specified in Q.763 (1999) is allowed to be used
-- The internal structure according to Q.763 (1999) is as follows:
-- Screening and presentation indicators 1 octet
-- Type of shape (ellipsoid point with uncertainty circle) 1 octet
-- Degrees of Latitude 3 octets
-- Degrees of Longitude 3 octets
-- Uncertainty code 1 octet
-- Confidence 1 octet

LocationNumber ::= OCTET STRING (SIZE (2..10))
-- the internal structure is defined in ITU-T Rec Q.763

SubscriberState ::= CHOICE {
               assumedIdle            [0] IMPLICIT NULL, 
               camelBusy              [1] IMPLICIT NULL, 
--XXX               netDetNotReachable     IMPLICIT NetDetNotReachable, 
               notProvidedFromVLR     [2] IMPLICIT NULL
} 
NetDetNotReachable ::=    ENUMERATED {
                  msPurged          ( 0 ), 
                  imsiDetached      ( 1 ), 
                  restrictedArea    ( 2 ), 
                  notRegistered     ( 3 ) }

PS-SubscriberState ::= CHOICE {
	notProvidedFromSGSN					[0] IMPLICIT NULL,
	ps-Detached							[1] IMPLICIT NULL,
	ps-AttachedNotReachableForPaging	[2] IMPLICIT NULL,
	ps-AttachedReachableForPaging		[3] IMPLICIT NULL,
	ps-PDP-ActiveNotReachableForPaging	[4] IMPLICIT PDP-ContextInfoList,
	ps-PDP-ActiveReachableForPaging		[5] IMPLICIT PDP-ContextInfoList,
	netDetNotReachable					NotReachableReason }

PDP-ContextInfoList ::= SEQUENCE SIZE (1..maxNumOfPDP-Contexts) OF PDP-ContextInfo

PDP-ContextInfo ::= SEQUENCE {
	pdp-ContextIdentifier			[0] IMPLICIT ContextId,
	pdp-ContextActive				[1] IMPLICIT NULL OPTIONAL,
	pdp-Type						[2] IMPLICIT PDP-Type,
	pdp-Address						[3] IMPLICIT PDP-Address OPTIONAL,
	apn-Subscribed					[4] IMPLICIT APN OPTIONAL,
	apn-InUse						[5] IMPLICIT APN OPTIONAL,
	nsapi							[6] IMPLICIT NSAPI OPTIONAL,
	transactionId					[7] IMPLICIT TransactionId OPTIONAL,
	teid-ForGnAndGp					[8] IMPLICIT TEID OPTIONAL,
	teid-ForIu						[9] IMPLICIT TEID OPTIONAL,
	ggsn-Address					[10] IMPLICIT GSN-Address OPTIONAL,
	qos-Subscribed					[11] IMPLICIT Ext-QoS-Subscribed OPTIONAL,
	qos-Requested					[12] IMPLICIT Ext-QoS-Subscribed OPTIONAL,
	qos-Negotiated					[13] IMPLICIT Ext-QoS-Subscribed OPTIONAL,
	chargingId						[14] IMPLICIT GPRSChargingID OPTIONAL,
	chargingCharacteristics			[15] IMPLICIT ChargingCharacteristics OPTIONAL,
	rnc-Address						[16] IMPLICIT GSN-Address OPTIONAL,
	extensionContainer				[17] IMPLICIT ExtensionContainer OPTIONAL,
	qos2-Subscribed					[18] IMPLICIT Ext2-QoS-Subscribed OPTIONAL,
-- qos2-Subscribed may be present only if qos-Subscribed is present.
	qos2-Requested					[19] IMPLICIT Ext2-QoS-Subscribed OPTIONAL,
-- qos2-Requested may be present only if qos-Requested is present.
	qos2-Negotiated [				20] IMPLICIT Ext2-QoS-Subscribed OPTIONAL
-- qos2-Negotiated may be present only if qos-Negotiated is present.
}

NSAPI ::= INTEGER (0..15)
-- This type is used to indicate the Network layer Service Access Point

TransactionId ::= OCTET STRING (SIZE (1..2))
-- This type carries the value part of the transaction identifier which is used in the
-- session management messages on the access interface. The encoding is defined in
-- 3GPP TS 24.008

TEID ::= OCTET STRING (SIZE (4))
-- This type carries the value part of the Tunnel Endpoint Identifier which is used to
-- distinguish between different tunnels between the same pair of entities which communicate
-- using the GPRS Tunnelling Protocol The encoding is defined in 3GPP TS 29.060.

GPRSChargingID ::= OCTET STRING (SIZE (4))
-- The Charging ID is a unique four octet value generated by the GGSN when
-- a PDP Context is activated. A Charging ID is generated for each activated context.
-- The encoding is defined in 3GPP TS 29.060.

NotReachableReason ::= ENUMERATED {
	msPurged (0),
	imsiDetached (1),
	restrictedArea (2),
	notRegistered (3)}

RoamingNumber ::= OCTET STRING ( SIZE( 1 .. 20 ) ) ( SIZE( 1 .. 9 ) ) 


Qos-Subscribed ::= OCTET STRING (  SIZE (1 .. 9 ) )

ExtSignalInfo ::= OCTET STRING ( SIZE( 1 .. 200 ) )

CUG-CheckInfo ::= SEQUENCE {
            cug-Interlock        CUG-Interlock, 
            cug-OutgoingAccess   NULL OPTIONAL, 
            extensionContainer   ExtensionContainer OPTIONAL
            }
ForwardingData ::= SEQUENCE {
                  forwardedToNumber			[5] IMPLICIT ISDN-AddressString OPTIONAL, 
                  forwardedToSubaddress		[4] IMPLICIT ISDN-SubaddressString OPTIONAL, 
                  forwardingOptions			[6] IMPLICIT ForwardingOptions OPTIONAL, 
                  extensionContainer		[7] IMPLICIT ExtensionContainer OPTIONAL,
				          longForwardedToNumber		[8] IMPLICIT FTN-AddressString OPTIONAL
                  }

Gmsc-Address ::= OCTET STRING ( SIZE( 1 .. 20 ) ) ( SIZE( 1 .. 9 ) )

--provideRoamingNumber OPERATION
--   ARGUMENT
ProvideRoamingNumberArg ::= SEQUENCE {
	imsi									[0] IMPLICIT IMSI,
	msc-Number								[1] IMPLICIT ISDN-AddressString,
	msisdn									[2] IMPLICIT ISDN-AddressString OPTIONAL,
	lmsi									[4] IMPLICIT LMSI OPTIONAL,
	gsm-BearerCapability					[5] IMPLICIT ExternalSignalInfo OPTIONAL,
	networkSignalInfo						[6] IMPLICIT ExternalSignalInfo OPTIONAL,
	suppressionOfAnnouncement				[7] IMPLICIT SuppressionOfAnnouncement OPTIONAL,
	gmsc-Address							[8] IMPLICIT ISDN-AddressString OPTIONAL,
	callReferenceNumber						[9] IMPLICIT CallReferenceNumber OPTIONAL,
	or-Interrogation						[10] IMPLICIT NULL OPTIONAL,
	extensionContainer						[11] IMPLICIT ExtensionContainer OPTIONAL,
	alertingPattern							[12] IMPLICIT AlertingPattern OPTIONAL,
	ccbs-Call								[13] IMPLICIT NULL OPTIONAL,
	supportedCamelPhasesInInterrogatingNode [15] IMPLICIT SupportedCamelPhases OPTIONAL,
	additionalSignalInfo					[14] IMPLICIT Ext-ExternalSignalInfo OPTIONAL,
	orNotSupportedInGMSC					[16] IMPLICIT NULL OPTIONAL,
	pre-pagingSupported						[17] IMPLICIT NULL OPTIONAL,
	longFTN-Supported						[18] IMPLICIT NULL OPTIONAL,
	suppress-VT-CSI							[19] IMPLICIT NULL OPTIONAL,
	offeredCamel4CSIsInInterrogatingNode	[20] IMPLICIT OfferedCamel4CSIs OPTIONAL
}

--   RESULT
ProvideRoamingNumberRes ::= SEQUENCE {
	roamingNumber							ISDN-AddressString,
	extensionContainer						ExtensionContainer OPTIONAL,
	releaseResourcesSupported				NULL OPTIONAL }

--   ERRORS {
-- systemFailure   localValue : 34, 
-- dataMissing   localValue : 35, 
-- unexpectedDataValue   localValue : 36, 
-- facilityNotSupported   localValue : 21, 
-- or-NotAllowed   localValue : 48, 
-- absentSubscriber   localValue : 27, 
-- noRoamingNumberAvailable   localValue : 39}
-- ::= localValue : 4

--resumeCallHandling OPERATION
--   ARGUMENT
ResumeCallHandlingArg ::= SEQUENCE {
	callReferenceNumber						[0] IMPLICIT CallReferenceNumber OPTIONAL,
	basicServiceGroup						[1] Ext-BasicServiceCode OPTIONAL,
	forwardingData							[2] IMPLICIT ForwardingData OPTIONAL,
	imsi									[3] IMPLICIT IMSI OPTIONAL,
	cug-CheckInfo							[4] IMPLICIT CUG-CheckInfo OPTIONAL,
	o-CSI									[5] IMPLICIT O-CSI OPTIONAL,
	extensionContainer						[7] IMPLICIT ExtensionContainer OPTIONAL,
	ccbs-Possible							[8] IMPLICIT NULL OPTIONAL,
	msisdn									[9] IMPLICIT ISDN-AddressString OPTIONAL,
	uu-Data									[10] IMPLICIT UU-Data OPTIONAL,
	allInformationSent						[11] IMPLICIT NULL OPTIONAL,
	d-csi									[12] IMPLICIT D-CSI OPTIONAL,
	o-BcsmCamelTDPCriteriaList				[13] IMPLICIT O-BcsmCamelTDPCriteriaList OPTIONAL,
	basicServiceGroup2						[14] IMPLICIT Ext-BasicServiceCode OPTIONAL
}

--   RESULT
ResumeCallHandlingRes ::= SEQUENCE {
         extensionContainer   ExtensionContainer OPTIONAL
         }
--   ERRORS {
-- forwardingFailed   localValue : 47, 
-- or-NotAllowed   localValue : 48, 
-- unexpectedDataValue   localValue : 36, 
-- dataMissing   localValue : 35}
-- ::= localValue : 6

UU-Data ::= SEQUENCE {
	uuIndicator				[0] IMPLICIT UUIndicator OPTIONAL,
	uui						[1] IMPLICIT UUI OPTIONAL,
	uusCFInteraction		[2] IMPLICIT NULL OPTIONAL,
	extensionContainer		[3] IMPLICIT ExtensionContainer OPTIONAL
  }

UUIndicator ::= OCTET STRING (SIZE (1))
-- Octets are coded according to ETS 300 356

UUI ::= OCTET STRING (SIZE (1..131))
-- Octets are coded according to ETS 300 356


--provideSIWFSNumber OPERATION
--   ARGUMENT

ProvideSIWFSNumberArg ::= SEQUENCE {
	gsm-BearerCapability	[0] IMPLICIT ExternalSignalInfo,
	isdn-BearerCapability	[1] IMPLICIT ExternalSignalInfo,
	call-Direction			[2] IMPLICIT CallDirection,
	b-Subscriber-Address	[3] IMPLICIT ISDN-AddressString,
	chosenChannel			[4] IMPLICIT ExternalSignalInfo,
	lowerLayerCompatibility [5] IMPLICIT ExternalSignalInfo OPTIONAL,
	highLayerCompatibility	[6] IMPLICIT ExternalSignalInfo OPTIONAL,
	extensionContainer		[7] IMPLICIT ExtensionContainer OPTIONAL
  }
--   RESULT
ProvideSIWFSNumberRes ::= SEQUENCE {
	sIWFSNumber				[0] IMPLICIT ISDN-AddressString,
	extensionContainer		[1] IMPLICIT ExtensionContainer OPTIONAL
  }
--   ERRORS {
-- resourceLimitation   localValue : 51, 
-- dataMissing   localValue : 35, 
-- unexpectedDataValue   localValue : 36, 
-- systemFailure   localValue : 34}
-- ::= localValue : 31

CallDirection ::= OCTET STRING (SIZE (1))
-- OCTET 1
-- bit 1 (direction of call)
-- 0 Mobile Originated Call (MOC)
-- 1 Mobile Terminated Call (MTC)


--sIWFSSignallingModify OPERATION
--   ARGUMENT
SIWFSSignallingModifyArg ::= SEQUENCE {
	channelType			[0] IMPLICIT ExternalSignalInfo OPTIONAL,
	chosenChannel		[1] IMPLICIT ExternalSignalInfo OPTIONAL,
	extensionContainer	[2] IMPLICIT ExtensionContainer OPTIONAL
  }
--   RESULT
SIWFSSignallingModifyRes ::= SEQUENCE {
	  channelType			[0] IMPLICIT ExternalSignalInfo OPTIONAL,
    extensionContainer  [1] IMPLICIT ExtensionContainer OPTIONAL
    }
--   ERRORS {
-- resourceLimitation   localValue : 51, 
-- dataMissing   localValue : 35, 
-- unexpectedDataValue   localValue : 36, 
-- systemFailure   localValue : 34}
-- ::= localValue : 32

Ccbs-Monitoring ::= ENUMERATED {
  stopMonitoring     ( 0 ), 
  startMonitoring    ( 1 )
  }

--setReportingState OPERATION
--   ARGUMENT
SetReportingStateArg ::= SEQUENCE {
	imsi				[0] IMSI OPTIONAL,
	lmsi				[1] LMSI OPTIONAL,
	ccbs-Monitoring		[2] ReportingState OPTIONAL,
	extensionContainer	[3] ExtensionContainer OPTIONAL
  }
--   RESULT

ReportingState ::= ENUMERATED {
	stopMonitoring (0),
	startMonitoring (1)
  }
-- exception handling:
-- reception of values 2-10 shall be mapped to 'stopMonitoring'
-- reception of values > 10 shall be mapped to 'startMonitoring'

CCBS-SubscriberStatus ::= ENUMERATED {
            ccbsNotIdle         ( 0 ), 
            ccbsIdle            ( 1 ), 
            ccbsNotReachable    ( 2 )
            }

SetReportingStateRes ::= SEQUENCE {
         ccbs-SubscriberStatus   [0] IMPLICIT CCBS-SubscriberStatus OPTIONAL, 
         extensionContainer      [1] IMPLICIT ExtensionContainer OPTIONAL
         }
--   ERRORS {
-- systemFailure   localValue : 34, 
-- unidentifiedSubscriber   localValue : 5, 
-- unexpectedDataValue   localValue : 36, 
-- dataMissing   localValue : 35, 
-- resourceLimitation   localValue : 51, 
-- facilityNotSupported   localValue : 21}
-- ::= localValue : 73


--statusReport OPERATION
--   ARGUMENT
StatusReportArg ::= SEQUENCE{
	imsi				[0] IMPLICIT IMSI,
	eventReportData		[1] IMPLICIT EventReportData OPTIONAL,
	callReportdata		[2] IMPLICIT CallReportData OPTIONAL,
	extensionContainer	[3] IMPLICIT ExtensionContainer OPTIONAL
  }
--   RESULT
StatusReportRes ::= SEQUENCE {
         extensionContainer   [0] IMPLICIT ExtensionContainer OPTIONAL
         }
--   ERRORS {
-- unknownSubscriber   localValue : 1, 
-- systemFailure   localValue : 34, 
-- unexpectedDataValue   localValue : 36, 
-- dataMissing   localValue : 35}
-- ::= localValue : 74

EventReportData ::= SEQUENCE{
	ccbs-SubscriberStatus	[0] IMPLICIT CCBS-SubscriberStatus OPTIONAL,
	extensionContainer		[1] IMPLICIT ExtensionContainer OPTIONAL
  }

CallReportData ::= SEQUENCE{
	monitoringMode		[0] IMPLICIT MonitoringMode OPTIONAL,
	callOutcome			[1] IMPLICIT CallOutcome OPTIONAL,
	extensionContainer	[2] IMPLICIT ExtensionContainer OPTIONAL
  }

MonitoringMode ::= ENUMERATED {
  a-side      ( 0 ), 
  b-side      ( 1 )
  }

CallOutcome ::= ENUMERATED {
  success     ( 0 ), 
  failure     ( 1 ), 
  busy        ( 2 )
  }

Ruf-Outcome ::= ENUMERATED {
  accepted                ( 0 ), 
  rejected                ( 1 ), 
  noResponseFromFreeMS    ( 2 ), 
  noResponseFromBusyMS    ( 3 ), 
  udubFromFreeMS          ( 4 ), 
  udubFromBusyMS          ( 5 )
  }

IST-AlertArg ::= SEQUENCE{
	imsi						[0] IMPLICIT IMSI,
	extensionContainer			[1] IMPLICIT ExtensionContainer OPTIONAL
  }

IST-AlertRes ::= SEQUENCE{
	istAlertTimer				[0] IMPLICIT IST-AlertTimerValue OPTIONAL,
	istInformationWithdraw		[1] IMPLICIT NULL OPTIONAL,
	callTerminationIndicator	[2] IMPLICIT CallTerminationIndicator OPTIONAL,
	extensionContainer			[3] IMPLICIT ExtensionContainer OPTIONAL
  }
--  ERRORS     {
--      unexpectedDataValue | 
--      resourceLimitation | 
--      unknownSubscriber | 
--      systemFailure | 
--      facilityNotSupported }
--   CODE     local      : 87
--   }

CallTerminationIndicator ::= ENUMERATED {
	terminateCallActivityReferred (0),
	terminateAllCallActivities (1)
  }
-- exception handling:
-- reception of values 2-10 shall be mapped to ' terminateCallActivityReferred '
-- reception of values > 10 shall be mapped to ' terminateAllCallActivities '
-- In MSCs not supporting linkage of all call activities, any value received shall
-- be interpreted as ' terminateCallActivityReferred '

IST-CommandArg ::= SEQUENCE{
	imsi						[0] IMPLICIT IMSI,
	extensionContainer			[1] IMPLICIT ExtensionContainer OPTIONAL
  }

IST-CommandRes ::= SEQUENCE{
	extensionContainer ExtensionContainer OPTIONAL
  }
--   ERRORS     {
--      unexpectedDataValue | 
--      resourceLimitation | 
--      unknownSubscriber | 
--      systemFailure | 
--      facilityNotSupported }
--   CODE     local      : 88
--   }

ReleaseResourcesArg ::= SEQUENCE{
	msrn						ISDN-AddressString OPTIONAL,
	extensionContainer			ExtensionContainer OPTIONAL
  }

ReleaseResourcesRes ::= SEQUENCE{
	extensionContainer			ExtensionContainer OPTIONAL
  }

--   ERRORS     {
--      unexpectedDataValue | 
--      systemFailure }
--   CODE     local      : 20
--   
--}

--remoteUserFree OPERATION
--   ARGUMENT
RemoteUserFreeArg ::= SEQUENCE{
	imsi				[0] IMPLICIT IMSI,
	callInfo			[1] IMPLICIT ExternalSignalInfo,
	ccbs-Feature		[2] IMPLICIT CCBS-Feature,
	translatedB-Number	[3] IMPLICIT ISDN-AddressString,
	replaceB-Number		[4] IMPLICIT NULL OPTIONAL,
	alertingPattern		[5] IMPLICIT AlertingPattern OPTIONAL,
	extensionContainer	[6] IMPLICIT ExtensionContainer OPTIONAL
  }

--   RESULT
RemoteUserFreeRes ::= SEQUENCE {
         ruf-Outcome          [0] IMPLICIT Ruf-Outcome, 
         extensionContainer   [1] IMPLICIT ExtensionContainer OPTIONAL
         }
--   ERRORS {
-- unexpectedDataValue   localValue : 36, 
-- dataMissing   localValue : 35, 
-- incompatibleTerminal   localValue : 28, 
-- absentSubscriber   localValue : 27, 
-- systemFailure   localValue : 34, 
-- busySubscriber   localValue : 45}
-- localValue : 75

TranslatedB-Number ::= OCTET STRING ( SIZE( 1 .. 20 ) ) ( SIZE( 1 .. 9 ) )

SS-Data ::= SEQUENCE {
	ss-Code					SS-Code OPTIONAL,
	ss-Status				[4] IMPLICIT SS-Status OPTIONAL,
	ss-SubscriptionOption	SS-SubscriptionOption OPTIONAL,
	basicServiceGroupList	BasicServiceGroupList OPTIONAL,
	defaultPriority			EMLPP-Priority OPTIONAL,
	nbrUser					[5] IMPLICIT MC-Bearers OPTIONAL
}

SS-SubscriptionOption ::= CHOICE {
	cliRestrictionOption	[2] IMPLICIT CliRestrictionOption,
	overrideCategory		[1] IMPLICIT OverrideCategory}

--registerSS OPERATION
--   ARGUMENT

RegisterSS-Arg ::= SEQUENCE {
	ss-Code						SS-Code,
	basicService				BasicServiceCode OPTIONAL,
	forwardedToNumber			[4] IMPLICIT AddressString OPTIONAL,
	forwardedToSubaddress		[6] IMPLICIT ISDN-SubaddressString OPTIONAL,
	noReplyConditionTime		[5] IMPLICIT NoReplyConditionTime OPTIONAL,
	defaultPriority				[7] IMPLICIT EMLPP-Priority OPTIONAL,
	nbrUser						[8] IMPLICIT MC-Bearers OPTIONAL,
	longFTN-Supported			[9] IMPLICIT NULL OPTIONAL }

NoReplyConditionTime ::= INTEGER (5..30)

--   RESULT
SS-Info ::= CHOICE {
	forwardingInfo		[0] IMPLICIT ForwardingInfo,
	callBarringInfo		[1] IMPLICIT CallBarringInfo,
	ss-Data				[3] IMPLICIT SS-Data}

--   ERRORS {
-- systemFailure   localValue : 34, 
-- dataMissing   localValue : 35, 
-- unexpectedDataValue   localValue : 36, 
-- bearerServiceNotProvisioned   localValue : 10, 
-- teleserviceNotProvisioned   localValue : 11, 
-- callBarred   localValue : 13, 
-- illegalSS-Operation   localValue : 16, 
-- ss-ErrorStatus   localValue : 17, 
-- ss-Incompatibility   localValue : 20}
-- ::= localValue : 10

B-subscriberNumber ::= OCTET STRING ( SIZE( 1 .. 20 ) ) ( SIZE( 1 .. 9 ) )

--eraseSS    OPERATION
--   ARGUMENT


--   RESULT
--Ss-Info ::=   CHOICE {.. defined elsewhere
--   ERRORS {
-- systemFailure   localValue : 34, 
-- dataMissing   localValue : 35, 
-- unexpectedDataValue   localValue : 36, 
-- bearerServiceNotProvisioned   localValue : 10, 
-- teleserviceNotProvisioned   localValue : 11, 
-- callBarred   localValue : 13, 
-- illegalSS-Operation   localValue : 16, 
-- ss-ErrorStatus   localValue : 17}
-- ::= localValue : 11

--activateSS OPERATION
--   ARGUMENT
--Ss-ForBS ::=  SEQUENCE {  defined elsewhere
--   RESULT
--Ss-Info ::=   CHOICE {.. defined elsewhere
--   ERRORS {
-- systemFailure   localValue : 34, 
-- dataMissing   localValue : 35, 
-- unexpectedDataValue   localValue : 36, 
-- bearerServiceNotProvisioned   localValue : 10, 
-- teleserviceNotProvisioned   localValue : 11, 
-- callBarred   localValue : 13, 
-- illegalSS-Operation   localValue : 16, 
-- ss-ErrorStatus   localValue : 17, 
-- ss-SubscriptionViolation   localValue : 19, 
-- ss-Incompatibility   localValue : 20, 
-- negativePW-Check   localValue : 38, 
-- numberOfPW-AttemptsViolation   localValue : 43}
-- ::= localValue : 12

--deactivateSS OPERATION
--  ARGUMENT
--Ss-ForBS ::=  SEQUENCE {  defined elsewhere
--   RESULT
--Ss-Info ::=   CHOICE {.. defined elsewhere
--   ERRORS {
-- systemFailure   localValue : 34, 
-- dataMissing   localValue : 35, 
-- unexpectedDataValue   localValue : 36, 
-- bearerServiceNotProvisioned   localValue : 10, 
-- teleserviceNotProvisioned   localValue : 11, 
-- callBarred   localValue : 13, 
-- illegalSS-Operation   localValue : 16, 
-- ss-ErrorStatus   localValue : 17, 
-- ss-SubscriptionViolation   localValue : 19, 
-- negativePW-Check   localValue : 38, 
-- numberOfPW-AttemptsViolation   localValue : 43}
-- ::= localValue : 13

--interrogateSS OPERATION
--  ARGUMENT
--Ss-ForBS ::=  SEQUENCE {  defined elsewhere
--   RESULT
InterrogateSS-Res ::= CHOICE {
	ss-Status				[0] IMPLICIT SS-Status,
	basicServiceGroupList	[2] IMPLICIT BasicServiceGroupList,
	forwardingFeatureList	[3] IMPLICIT ForwardingFeatureList,
	genericServiceInfo		[4] IMPLICIT GenericServiceInfo }

--   ERRORS {
-- systemFailure   localValue : 34, 
-- dataMissing   localValue : 35, 
-- unexpectedDataValue   localValue : 36, 
-- bearerServiceNotProvisioned   localValue : 10, 
-- teleserviceNotProvisioned   localValue : 11, 
-- callBarred   localValue : 13, 
-- illegalSS-Operation   localValue : 16, 
-- ss-NotAvailable   localValue : 18}
-- ::= localValue : 14




--processUnstructuredSS-Request OPERATION
--   ARGUMENT
Ussd-Arg ::=  SEQUENCE {
	       ussd-DataCodingScheme		USSD-DataCodingScheme,
	       ussd-String					USSD-String,
         alertingPattern         AlertingPattern OPTIONAL, 
         msisdn                  [0] IMPLICIT ISDN-AddressString OPTIONAL}
--   RESULT
Ussd-Res ::=  SEQUENCE {
	ussd-DataCodingScheme	USSD-DataCodingScheme,
	ussd-String				USSD-String
  }
--   ERRORS {
-- systemFailure   localValue : 34, 
-- dataMissing   localValue : 35, 
-- unexpectedDataValue   localValue : 36, 
-- unknownAlphabet   localValue : 71, 
-- callBarred   localValue : 13}
-- ::= localValue : 59

USSD-DataCodingScheme ::= OCTET STRING (SIZE (1))
-- The structure of the USSD-DataCodingScheme is defined by
-- the Cell Broadcast Data Coding Scheme as described in
-- TS 3GPP TS 23.038 [25]

USSD-String ::= OCTET STRING (SIZE (1..160))
-- The structure of the contents of the USSD-String is dependent
-- on the USSD-DataCodingScheme as described in TS 3GPP TS 23.038 [25].

--unstructuredSS-Request OPERATION
--   ARGUMENT
--ussd-Arg ::=  SEQUENCE { .. defined elsewhere
--   RESULT
--ussd-Res ::=  SEQUENCE { ... defined elsewhere
--   ERRORS {
-- systemFailure   localValue : 34, 
-- dataMissing   localValue : 35, 
-- unexpectedDataValue   localValue : 36, 
-- absentSubscriber   localValue : 27, 
-- illegalSubscriber   localValue : 9, 
-- illegalEquipment   localValue : 12, 
-- unknownAlphabet   localValue : 71, 
-- ussd-Busy   localValue : 72}
-- ::= localValue : 60

--unstructuredSS-Notify OPERATION
--   ARGUMENT
--ussd-Arg ::=  SEQUENCE { .. defined elsewhere
--   ERRORS {
-- systemFailure   localValue : 34, 
-- dataMissing   localValue : 35, 
-- unexpectedDataValue   localValue : 36, 
-- absentSubscriber   localValue : 27, 
-- illegalSubscriber   localValue : 9, 
-- illegalEquipment   localValue : 12, 
-- unknownAlphabet   localValue : 71, 
-- ussd-Busy   localValue : 72}
-- ::= localValue : 61

AuthenticationFailureReportArg ::= SEQUENCE {	
	imsi					IMSI,
	failureCause			FailureCause,
	extensionContainer		ExtensionContainer OPTIONAL,
	re-attempt				BOOLEAN OPTIONAL,
	accessType				AccessType OPTIONAL,
	rand					RAND OPTIONAL,
	vlr-Number				[0] IMPLICIT ISDN-AddressString OPTIONAL,
	sgsn-Number				[1] IMPLICIT ISDN-AddressString OPTIONAL }

AccessType ::= ENUMERATED {
	call (0),
	emergencyCall (1),
	locationUpdating (2),
	supplementaryService (3),
	shortMessage (4),
	gprsAttach (5),
	routingAreaUpdating (6),
	serviceRequest (7),
	pdpContextActivation (8),
	pdpContextDeactivation (9),
	gprsDetach (10)}
-- exception handling:
-- received values greater than 10 shall be ignored.

AuthenticationFailureReportRes ::= SEQUENCE {
	extensionContainer		ExtensionContainer OPTIONAL
  }

FailureCause ::= ENUMERATED {
	wrongUserResponse (0),
	wrongNetworkSignature (1)}

--registerPassword OPERATION
--   ARGUMENT
SS-Code  ::=  OCTET STRING
--   RESULT
NewPassword ::= NumericString (SIZE( 4 ) )
--   ERRORS {
-- systemFailure   localValue : 34, 
-- dataMissing   localValue : 35, 
-- unexpectedDataValue   localValue : 36, 
-- callBarred   localValue : 13, 
-- ss-SubscriptionViolation   localValue : 19, 
-- pw-RegistrationFailure   localValue : 37, 
-- negativePW-Check   localValue : 38, 
-- numberOfPW-AttemptsViolation   localValue : 43}
--LINKED {
     -- getPassword   localValue : 18}
-- ::= localValue : 17

--getPassword OPERATION
--   ARGUMENT
GetPasswordArg ::= ENUMERATED {
         enterPW             ( 0 ), 
         enterNewPW          ( 1 ), 
         enterNewPW-Again    ( 2 ) }
--   RESULT
CurrentPassword ::= NumericString (SIZE( 4 ) )
-- ::= localValue : 18

--registerCC-Entry OPERATION
--   ARGUMENT

RegisterCC-EntryArg ::= SEQUENCE {
	ss-Code			[0] IMPLICIT SS-Code,
	ccbs-Data		[1] IMPLICIT CCBS-Data OPTIONAL
  }
--   RESULT
RegisterCC-EntryRes ::= SEQUENCE {
         ccbs-Feature   [0] IMPLICIT CCBS-Feature OPTIONAL
         }
--   ERRORS {
-- systemFailure   localValue : 34, 
-- dataMissing   localValue : 35, 
-- unexpectedDataValue   localValue : 36, 
-- callBarred   localValue : 13, 
-- illegalSS-Operation   localValue : 16, 
-- ss-ErrorStatus   localValue : 17, 
-- ss-Incompatibility   localValue : 20, 
-- shortTermDenial   localValue : 29, 
-- longTermDenial   localValue : 30, 
-- facilityNotSupported   localValue : 21}
-- ::= localValue : 76

CCBS-Data ::= SEQUENCE {
	ccbs-Feature		[0] CCBS-Feature,
	translatedB-Number	[1] ISDN-AddressString,
	serviceIndicator	[2] ServiceIndicator OPTIONAL,
	callInfo			[3] ExternalSignalInfo,
	networkSignalInfo	[4] ExternalSignalInfo
  }

ServiceIndicator ::= BIT STRING {
	clir-invoked (0),
	camel-invoked (1)} (SIZE(2..32))
-- exception handling:
-- bits 2 to 31 shall be ignored if received and not understood

--eraseCC-Entry OPERATION
--   ARGUMENT
EraseCC-EntryArg ::= SEQUENCE {
         ss-Code      [0] IMPLICIT SS-Code, 
         ccbs-Index   [1] IMPLICIT CCBS-Index
         }
--   RESULT
EraseCC-EntryRes ::= SEQUENCE {
         ss-Code     [0] IMPLICIT SS-Code, 
         ss-Status   [1] IMPLICIT SS-Status OPTIONAL
         }
--   ERRORS {
-- systemFailure   localValue : 34, 
-- dataMissing   localValue : 35, 
-- unexpectedDataValue   localValue : 36, 
-- callBarred   localValue : 13, 
-- illegalSS-Operation   localValue : 16, 
-- ss-ErrorStatus   localValue : 17}
-- ::= localValue : 77

--sendRoutingInfoForSM OPERATION
--   ARGUMENT
RoutingInfoForSMArg ::= SEQUENCE {
         msisdn                 [0] IMPLICIT ISDN-AddressString, 
         sm-RP-PRI              [1] IMPLICIT BOOLEAN, 
         serviceCentreAddress   [2] IMPLICIT ServiceCentreAddress, 
         extensionContainer     [6] IMPLICIT ExtensionContainer OPTIONAL, 
         gprsSupportIndicator   [7] IMPLICIT NULL OPTIONAL, 
         sm-RP-MTI              [8] IMPLICIT INTEGER ( 0 .. 10 ) OPTIONAL, 
         sm-RP-SMEA             [9] IMPLICIT OCTET STRING ( SIZE( 1 .. 12 ) ) OPTIONAL}
--   RESULT

RoutingInfoForSM-Res ::= SEQUENCE {
	imsi IMSI,
	locationInfoWithLMSI	[0] IMPLICIT LocationInfoWithLMSI,
	extensionContainer		[4] IMPLICIT ExtensionContainer OPTIONAL
  }

LocationInfoWithLMSI ::= SEQUENCE {
	networkNode-Number	[1] IMPLICIT ISDN-AddressString,
	lmsi				LMSI OPTIONAL,
	extensionContainer	ExtensionContainer OPTIONAL,
	gprsNodeIndicator	[5] IMPLICIT NULL OPTIONAL,
-- gprsNodeIndicator is set only if the SGSN number is sent as the
-- Network Node Number
	additional-Number	[6] IMPLICIT Additional-Number OPTIONAL
-- NetworkNode-number can be either msc-number or sgsn-number
}

Additional-Number ::= CHOICE {
	msc-Number	[0] IMPLICIT ISDN-AddressString,
	sgsn-Number [1] IMPLICIT ISDN-AddressString}
-- additional-number can be either msc-number or sgsn-number
-- if received networkNode-number is msc-number then the
-- additional number is sgsn-number
-- if received networkNode-number is sgsn-number then the
-- additional number is msc-number

--   ERRORS {
-- systemFailure   localValue : 34, 
-- dataMissing   localValue : 35, 
-- unexpectedDataValue   localValue : 36, 
-- facilityNotSupported   localValue : 21, 
-- unknownSubscriber   localValue : 1, 
-- teleserviceNotProvisioned   localValue : 11, 
-- callBarred   localValue : 13, 
-- absentsubscriberSM   localValue : 6}
-- ::= localValue : 45

--mo-forwardSM OPERATION
--   ARGUMENT
Mo-forwardSM-Arg ::= SEQUENCE {
         sm-RP-DA             Sm-RP-DA, 
         sm-RP-OA             Sm-RP-OA, 
         sm-RP-UI             Sm-RP-UI, 
         extensionContainer   ExtensionContainer OPTIONAL,
         imsi                 IMSI OPTIONAL}
--   RESULT
Mo-forwardSM-Res ::= SEQUENCE {
         sm-RP-UI             Sm-RP-UI OPTIONAL, 
         extensionContainer   ExtensionContainer OPTIONAL
         }
--   ERRORS {
-- systemFailure   localValue : 34, 
-- unexpectedDataValue   localValue : 36, 
-- facilityNotSupported   localValue : 21, 
-- sm-DeliveryFailure   localValue : 32}
-- ::= localValue : 46

Sm-RP-OA ::= CHOICE {
            msisdn                     [2] IMPLICIT ISDN-AddressString, 
            serviceCentreAddressOA     [4] IMPLICIT ServiceCentreAddress, 
            noSM-RP-OA                 [5] IMPLICIT NULL}

Sm-RP-DA ::= CHOICE {
            imsi                       [0] IMPLICIT IMSI, 
            lmsi                       [1] IMPLICIT LMSI, 
            serviceCentreAddressDA     [4] IMPLICIT ServiceCentreAddress, 
            noSM-RP-DA                 [5] IMPLICIT NULL
}

Sm-RP-UI ::= OCTET STRING ( SIZE( 1 .. 200 ) )
ServiceCentreAddress ::= OCTET STRING ( SIZE( 1 .. 20 ) )

--mt-forwardSM OPERATION
--   ARGUMENT
Mt-forwardSM-Arg ::= SEQUENCE {
         sm-RP-DA             Sm-RP-DA, 
         sm-RP-OA             Sm-RP-OA, 
         sm-RP-UI             Sm-RP-UI, 
         moreMessagesToSend   NULL OPTIONAL, 
         extensionContainer   ExtensionContainer OPTIONAL
         }
--   RESULT
Mt-forwardSM-Res ::= SEQUENCE {
         sm-RP-UI             Sm-RP-UI OPTIONAL, 
         extensionContainer   ExtensionContainer OPTIONAL
         }
--   ERRORS {
-- systemFailure   localValue : 34, 
-- dataMissing   localValue : 35, 
-- unexpectedDataValue   localValue : 36, 
-- facilityNotSupported   localValue : 21, 
-- unidentifiedSubscriber   localValue : 5, 
-- illegalSubscriber   localValue : 9, 
-- illegalEquipment   localValue : 12, 
-- subscriberBusyForMT-SMS   localValue : 31, 
-- sm-DeliveryFailure   localValue : 32, 
-- absentsubscriberSM   localValue : 6}
-- ::= localValue : 44


StoredMSISDN ::= ISDN-AddressString


Sm-DeliveryOutcome ::= ENUMERATED {
  memoryCapacityExceeded    ( 0 ), 
  absentSubscriber          ( 1 ), 
  successfulTransfer        ( 2 ) }

--reportSM-DeliveryStatus OPERATION
--  ARGUMENT
ReportSM-DeliveryStatusArg ::= SEQUENCE {
         msisdn                                   ISDN-AddressString, 
         serviceCentreAddress                     ServiceCentreAddress, 
         sm-DeliveryOutcome                       Sm-DeliveryOutcome, 
         absentSubscriberDiagnosticSM             [0] IMPLICIT AbsentSubscriberDiagnosticSM OPTIONAL, 
         extensionContainer                       [1] IMPLICIT ExtensionContainer OPTIONAL, 
         gprsSupportIndicator                     [2] IMPLICIT NULL OPTIONAL, 
         deliveryOutcomeIndicator                 [3] IMPLICIT NULL OPTIONAL, 
         additionalSM-DeliveryOutcome             [4] IMPLICIT Sm-DeliveryOutcome OPTIONAL, 
         additionalAbsentSubscriberDiagnosticSM   [5] IMPLICIT AbsentSubscriberDiagnosticSM OPTIONAL}
--   RESULT
ReportSM-DeliveryStatusRes ::= SEQUENCE {
         storedMSISDN         StoredMSISDN OPTIONAL, 
         extensionContainer   ExtensionContainer OPTIONAL
         }
--   ERRORS {
-- dataMissing   localValue : 35, 
-- unexpectedDataValue   localValue : 36, 
-- unknownSubscriber   localValue : 1, 
-- messageWaitingListFull   localValue : 33}
-- ::= localValue : 47

--informServiceCentre OPERATION
--   ARGUMENT
InformServiceCentreArg ::= SEQUENCE {
         storedMSISDN         StoredMSISDN OPTIONAL, 
         mw-Status            BIT STRING {
            scAddressNotIncluded  (0 ), 
            mnrfSet  (1 ), 
            mcefSet  (2 ), 
            mnrgSet  (3 )} ( SIZE( 6 .. 16 ) ) OPTIONAL, 
         extensionContainer   ExtensionContainer OPTIONAL }
-- ::= localValue : 63

--alertServiceCentre OPERATION
--   ARGUMENT
AlertServiceCentreArg ::= SEQUENCE {
         msisdn                 ISDN-AddressString, 
         serviceCentreAddress   ServiceCentreAddress
         }
--   ERRORS {
-- systemFailure   localValue : 34, 
-- dataMissing   localValue : 35, 
-- unexpectedDataValue   localValue : 36}
-- ::= localValue : 64

--readyForSM OPERATION
--   ARGUMENT
ReadyForSM-Arg ::= SEQUENCE {
         imsi                   [0] IMPLICIT IMSI, 
         alertReason            ENUMERATED {
            msPresent         ( 0 ), 
            memoryAvailable    ( 1 ) }, 
         alertReasonIndicator   NULL OPTIONAL, 
         extensionContainer     ExtensionContainer OPTIONAL
         }
--   RESULT
ReadyForSM-Res ::= SEQUENCE {
         extensionContainer   ExtensionContainer OPTIONAL
         }
--   ERRORS {
-- dataMissing   localValue : 35, 
-- unexpectedDataValue   localValue : 36, 
-- facilityNotSupported   localValue : 21, 
-- unknownSubscriber   localValue : 1}
-- ::= localValue : 66

--provideSubscriberInfo OPERATION
--   ARGUMENT
ProvideSubscriberInfoArg ::= SEQUENCE {
         imsi                 [0] IMPLICIT IMSI, 
         lmsi                 [1] IMPLICIT LMSI OPTIONAL, 
         requestedInfo        [2] IMPLICIT RequestedInfo, 
         extensionContainer   [3] IMPLICIT ExtensionContainer OPTIONAL
         }
--   RESULT
ProvideSubscriberInfoRes ::= SEQUENCE {
         subscriberInfo       SubscriberInfo, 
         extensionContainer   ExtensionContainer OPTIONAL
         }
--   ERRORS {
-- dataMissing   localValue : 35, 
-- unexpectedDataValue   localValue : 36}
-- ::= localValue : 70

SubscriberInfo ::= SEQUENCE {
	locationInformation			[0] IMPLICIT LocationInformation OPTIONAL,
	subscriberState				[1] SubscriberState OPTIONAL,
	extensionContainer			[2] IMPLICIT ExtensionContainer OPTIONAL,
	locationInformationGPRS		[3] IMPLICIT LocationInformationGPRS OPTIONAL,
	ps-SubscriberState			[4] IMPLICIT PS-SubscriberState OPTIONAL,
	imei						[5] IMPLICIT IMEI OPTIONAL,
	ms-Classmark2				[6] IMPLICIT MS-Classmark2 OPTIONAL,
	gprs-MS-Class				[7] IMPLICIT GPRSMSClass OPTIONAL,
	mnpInfoRes					[8] IMPLICIT MNPInfoRes OPTIONAL }
-- If the HLR receives locationInformation, subscriberState or ms-Classmark2 from an SGSN
-- it shall discard them.
-- If the HLR receives locationInformationGPRS, ps-SubscriberState or gprs-MS-Class from
-- a VLR it shall discard them.
-- If the HLR receives parameters which it has not requested, it shall discard them.

MNPInfoRes ::= SEQUENCE {
	routeingNumber			[0] IMPLICIT RouteingNumber OPTIONAL,
	imsi					[1] IMPLICIT IMSI OPTIONAL,
	msisdn					[2] IMPLICIT ISDN-AddressString OPTIONAL,
	numberPortabilityStatus [3] IMPLICIT NumberPortabilityStatus OPTIONAL,
	extensionContainer		[4] IMPLICIT ExtensionContainer OPTIONAL
  }
-- The IMSI parameter contains a generic IMSI, i.e. it is not tied necessarily to the
-- Subscriber. MCC and MNC values in this IMSI shall point to the Subscription Network of
-- the Subscriber. See 3GPP TS 23.066 [108].

RouteingNumber ::= TBCD-STRING (SIZE (1..5))

NumberPortabilityStatus ::=  ENUMERATED {
               notKnownToBePorted                     (0 ), 
               ownNumberPortedOut                     (1 ), 
               foreignNumberPortedToForeignNetwork    (2 ),  
               ownNumberNotPortedOut                  (4 ), 
               foreignNumberPortedIn                  (5 )
			   }
-- exception handling:
-- reception of other values than the ones listed the receiver shall ignore the
-- whole NumberPortabilityStatus;
-- ownNumberNotPortedOut or foreignNumberPortedIn may only be included in Any Time
-- Interrogation message.

MS-Classmark2 ::= OCTET STRING (SIZE (3))
-- This parameter carries the value part of the MS Classmark 2 IE defined in
-- 3GPP TS 24.008 [35].

GPRSMSClass ::= SEQUENCE {
	mSNetworkCapability			[0] IMPLICIT MSNetworkCapability,
	mSRadioAccessCapability		[1] IMPLICIT MSRadioAccessCapability OPTIONAL
}

MSNetworkCapability ::= OCTET STRING (SIZE (1..8))
-- This parameter carries the value part of the MS Network Capability IE defined in
-- 3GPP TS 24.008 [35].

MSRadioAccessCapability ::= OCTET STRING (SIZE (1..50))
-- This parameter carries the value part of the MS Radio Access Capability IE defined in
-- 3GPP TS 24.008 [35].

RequestedInfo ::= SEQUENCE {
            locationInformation   [0] IMPLICIT NULL OPTIONAL, 
            subscriberState       [1] IMPLICIT NULL OPTIONAL, 
            extensionContainer    [2] IMPLICIT ExtensionContainer OPTIONAL,
            currentLocation       [3] IMPLICIT NULL OPTIONAL, 
            requestedDomain       [4] IMPLICIT ENUMERATED {
               cs-Domain    (0 ), 
               ps-Domain    (1 )
               } OPTIONAL, 
            imei                  [6] IMPLICIT NULL OPTIONAL, 
            ms-classmark          [5] IMPLICIT NULL OPTIONAL, 
            mnpRequestedInfo      [7] IMPLICIT NULL OPTIONAL
            }
--anyTimeInterrogation OPERATION
--   ARGUMENT
AnyTimeInterrogationArg ::= SEQUENCE {
         subscriberIdentity   [0] SubscriberIdentity, 
         requestedInfo        [1] IMPLICIT RequestedInfo, 
         gsmSCF-Address       [3] IMPLICIT ISDN-AddressString, 
         extensionContainer   [2] IMPLICIT ExtensionContainer OPTIONAL
         }
--   RESULT
AnyTimeInterrogationRes ::= SEQUENCE {
         subscriberInfo       SubscriberInfo, 
         extensionContainer   ExtensionContainer OPTIONAL
         }
--   ERRORS {
-- systemFailure   localValue : 34, 
-- ati-NotAllowed   localValue : 49, 
-- dataMissing   localValue : 35, 
-- unexpectedDataValue   localValue : 36, 
-- unknownSubscriber   localValue : 1}
-- ::= localValue : 71

-- anyTimeSubscriptionInterrogation OPERATION  ::=  {
--   ARGUMENT     SEQUENCE {
AnyTimeSubscriptionInterrogationArg ::= SEQUENCE {
	subscriberIdentity			[0] IMPLICIT SubscriberIdentity,
	requestedSubscriptionInfo	[1] IMPLICIT RequestedSubscriptionInfo,
	gsmSCF-Address				[2] IMPLICIT ISDN-AddressString,
	extensionContainer			[3] IMPLICIT ExtensionContainer OPTIONAL,
	longFTN-Supported			[4] IMPLICIT NULL OPTIONAL
  }

--   RESULT     SEQUENCE {
AnyTimeSubscriptionInterrogationRes ::= SEQUENCE {
	callForwardingData				[1] IMPLICIT CallForwardingData OPTIONAL,
	callBarringData					[2] IMPLICIT CallBarringData OPTIONAL,
	odb-Info						[3] IMPLICIT ODB-Info OPTIONAL,
	camel-SubscriptionInfo			[4] IMPLICIT CAMEL-SubscriptionInfo OPTIONAL,
	supportedVLR-CAMEL-Phases		[5] IMPLICIT SupportedCamelPhases OPTIONAL,
	supportedSGSN-CAMEL-Phases		[6] IMPLICIT SupportedCamelPhases OPTIONAL,
	extensionContainer				[7] IMPLICIT ExtensionContainer OPTIONAL,
	offeredCamel4CSIsInVLR			[8] IMPLICIT OfferedCamel4CSIs OPTIONAL,
	offeredCamel4CSIsInSGSN			[9] IMPLICIT OfferedCamel4CSIs OPTIONAL }

--   ERRORS     {
--      atsi-NotAllowed | 
--      dataMissing | 
--      unexpectedDataValue | 
--      unknownSubscriber | 
--      bearerServiceNotProvisioned | 
--     teleserviceNotProvisioned | 
--      callBarred | 
--      illegalSS-Operation | 
--      ss-NotAvailable | 
--      informationNotAvailable }
--   CODE     local      : 62
--   }

RequestedSubscriptionInfo ::= SEQUENCE {
	requestedSS-Info							[1] IMPLICIT SS-ForBS-Code OPTIONAL,
	odb											[2] IMPLICIT NULL OPTIONAL,
	requestedCAMEL-SubscriptionInfo				[3] IMPLICIT RequestedCAMEL-SubscriptionInfo OPTIONAL,
	supportedVLR-CAMEL-Phases					[4] IMPLICIT NULL OPTIONAL,
	supportedSGSN-CAMEL-Phases					[5] IMPLICIT NULL OPTIONAL,
	extensionContainer							[6] IMPLICIT ExtensionContainer OPTIONAL,
	additionalRequestedCAMEL-SubscriptionInfo
												[7] AdditionalRequestedCAMEL-SubscriptionInfo
OPTIONAL }

RequestedCAMEL-SubscriptionInfo ::= ENUMERATED {
	o-CSI (0),
	t-CSI (1),
	vt-CSI (2),
	tif-CSI (3),
	gprs-CSI (4),
	mo-sms-CSI (5),
	ss-CSI (6),
	m-CSI (7),
	d-csi (8)}

AdditionalRequestedCAMEL-SubscriptionInfo ::= ENUMERATED {
	mt-sms-CSI (0),
	mg-csi (1),
	o-IM-CSI (2),
	d-IM-CSI (3),
	vt-IM-CSI (4)
  }
-- exception handling: unknown values shall be discarded by the receiver.

CallForwardingData ::= SEQUENCE {
	forwardingFeatureList		Ext-ForwFeatureList,
	notificationToCSE			NULL OPTIONAL,
	extensionContainer			[0] IMPLICIT ExtensionContainer OPTIONAL
  }

CallBarringData ::= SEQUENCE {
	callBarringFeatureList			Ext-CallBarFeatureList,
	password						Password OPTIONAL,
	wrongPasswordAttemptsCounter	WrongPasswordAttemptsCounter OPTIONAL,
	notificationToCSE				NULL OPTIONAL,
	extensionContainer				ExtensionContainer OPTIONAL
  }

--Password ::= NumericString ( FROM ("0"|"1"|"2"|"3"|"4"|"5"|"6"|"7"|"8"|"9" )) (SIZE( 4 ) )
Password ::= NumericString (SIZE( 4 ) )

BasicServiceCode ::= CHOICE {
	bearerService	[2] IMPLICIT BearerServiceCode,
	teleservice		[3] IMPLICIT TeleserviceCode}

BearerServiceCode ::= OCTET STRING (SIZE (1))
-- This type is used to represent the code identifying a single
-- bearer service, a group of bearer services, or all bearer
-- services. The services are defined in TS 3GPP TS 22.002 [3].
-- The internal structure is defined as follows:
--
-- plmn-specific bearer services:
-- bits 87654321: defined by the HPLMN operator
-- rest of bearer services:
-- bit 8: 0 (unused)
-- bits 7654321: group (bits 7654), and rate, if applicable
-- (bits 321)

TeleserviceCode ::= OCTET STRING (SIZE (1))
-- This type is used to represent the code identifying a single
-- teleservice, a group of teleservices, or all teleservices. The
-- services are defined in TS GSM 22.003 [4].
-- The internal structure is defined as follows:
-- bits 87654321: group (bits 8765) and specific service
-- (bits 4321)

O-BcsmCamelTDPCriteriaList ::= SEQUENCE SIZE (1..10) OF
O-BcsmCamelTDP-Criteria

T-BCSM-CAMEL-TDP-CriteriaList ::= SEQUENCE SIZE (1..10) OF
T-BCSM-CAMEL-TDP-Criteria

O-BcsmCamelTDP-Criteria ::= SEQUENCE {
	o-BcsmTriggerDetectionPoint		O-BcsmTriggerDetectionPoint,
	destinationNumberCriteria		[0] IMPLICIT DestinationNumberCriteria OPTIONAL,
	basicServiceCriteria			[1] IMPLICIT BasicServiceCriteria OPTIONAL,
	callTypeCriteria				[2] IMPLICIT CallTypeCriteria OPTIONAL,
	o-CauseValueCriteria			[3] IMPLICIT O-CauseValueCriteria OPTIONAL,
	extensionContainer				[4] IMPLICIT ExtensionContainer OPTIONAL }

T-BCSM-CAMEL-TDP-Criteria ::= SEQUENCE {
	t-BCSM-TriggerDetectionPoint	T-BcsmTriggerDetectionPoint,
	basicServiceCriteria			[0] IMPLICIT BasicServiceCriteria OPTIONAL,
	t-CauseValueCriteria			[1] IMPLICIT T-CauseValueCriteria OPTIONAL
  }

O-BcsmTriggerDetectionPoint ::= ENUMERATED {
	collectedInfo (2),
	routeSelectFailure (4) }
-- exception handling:
-- For O-BcsmCamelTDPData sequences containing this parameter with any
-- other value than the ones listed the receiver shall ignore the whole
-- O-BcsmCamelTDPDatasequence.
-- For O-BcsmCamelTDP-Criteria sequences containing this parameter with any
-- other value than the ones listed the receiver shall ignore the whole
-- O-BcsmCamelTDP-Criteria sequence.

T-BcsmTriggerDetectionPoint ::= ENUMERATED {
	termAttemptAuthorized (12),
	tBusy (13),
	tNoAnswer (14)}
-- exception handling:
-- For T-BcsmCamelTDPData sequences containing this parameter with any other
-- value than the ones listed above, the receiver shall ignore the whole
-- T-BcsmCamelTDPData sequence.


WrongPasswordAttemptsCounter ::= INTEGER (0..4)

OfferedCamel4CSIs ::= BIT STRING {
	o-csi (0),
	d-csi (1),
	vt-csi (2),
	t-csi (3),
	mt-sms-csi (4),
	mg-csi (5),
	psi-enhancements (6)
} (SIZE (7..16))
-- A node supporting Camel phase 4 shall mark in the BIT STRING all Camel4 CSIs
-- it offers.
-- Other values than listed above shall be discarded.

OfferedCamel4Functionalities ::= BIT STRING {
	initiateCallAttempt (0),
	splitLeg (1),
	moveLeg (2),
	disconnectLeg (3),
	entityReleased (4),
	dfc-WithArgument (5),
	playTone (6),
	dtmf-MidCall (7),
	chargingIndicator (8),
	alertingDP (9),
	locationAtAlerting (10),
	changeOfPositionDP (11),
	or-Interactions (12),
	warningToneEnhancements (13),
	cf-Enhancements (14),
	subscribedEnhancedDialledServices (15),
	servingNetworkEnhancedDialledServices (16),
	criteriaForChangeOfPositionDP (17),
	serviceChangeDP (18)
} (SIZE (15..64))
-- A node supporting Camel phase 4 shall mark in the BIT STRING all CAMEL4
-- functionalities it offers.
-- Other values than listed above shall be discarded.


SS-ForBS-Code ::= SEQUENCE {
	ss-Code				SS-Code,
	basicService		BasicServiceCode OPTIONAL,
	longFTN-Supported	[4] IMPLICIT NULL OPTIONAL }

GenericServiceInfo ::= SEQUENCE {
	ss-Status					SS-Status,
	cliRestrictionOption		CliRestrictionOption OPTIONAL,
	maximumEntitledPriority		[0] IMPLICIT EMLPP-Priority OPTIONAL,
	defaultPriority				[1] IMPLICIT EMLPP-Priority OPTIONAL,
	ccbs-FeatureList			[2] IMPLICIT CCBS-FeatureList OPTIONAL,
	nbrSB						[3] IMPLICIT MaxMC-Bearers OPTIONAL,
	nbrUser						[4] IMPLICIT MC-Bearers OPTIONAL,
	nbrSN						[5] IMPLICIT MC-Bearers OPTIONAL }

CCBS-FeatureList ::= SEQUENCE SIZE (1..5) OF CCBS-Feature

CCBS-Feature ::= SEQUENCE {
	ccbs-Index				[0] IMPLICIT CCBS-Index OPTIONAL,
	b-subscriberNumber		[1] IMPLICIT ISDN-AddressString OPTIONAL,
	b-subscriberSubaddress	[2] IMPLICIT ISDN-SubaddressString OPTIONAL,
	basicServiceGroup		[3] IMPLICIT BasicServiceCode OPTIONAL
  }

CCBS-Index ::= INTEGER (1..5)

T-CauseValueCriteria ::= SEQUENCE SIZE(1..5) OF
CauseValue

O-CauseValueCriteria ::= SEQUENCE SIZE(1..5) OF
CauseValue

CauseValue ::= OCTET STRING (SIZE(1))
-- Type extracted from Cause parameter in ITU-T Recommendation Q.763.
-- For the use of cause value refer to ITU-T Recommendation Q.850.



BasicServiceCriteria ::= SEQUENCE SIZE(1..5) OF
Ext-BasicServiceCode

--anyTimeModification OPERATION  ::=  {
--   ARGUMENT     SEQUENCE {

AnyTimeModificationArg ::= SEQUENCE {
	subscriberIdentity				[0] IMPLICIT SubscriberIdentity,
	gsmSCF-Address					[1] IMPLICIT ISDN-AddressString,
	modificationRequestFor-CF-Info	[2] IMPLICIT ModificationRequestFor-CF-Info OPTIONAL,
	modificationRequestFor-CB-Info	[3] IMPLICIT ModificationRequestFor-CB-Info OPTIONAL,
	modificationRequestFor-CSI		[4] IMPLICIT ModificationRequestFor-CSI OPTIONAL,
	extensionContainer				[5] IMPLICIT ExtensionContainer OPTIONAL,
	longFTN-Supported				[6] IMPLICIT NULL OPTIONAL,
modificationRequestFor-ODB-data [7] ModificationRequestFor-ODB-data OPTIONAL }

--   RESULT     SEQUENCE {
AnyTimeModificationRes ::= SEQUENCE {
	ss-InfoFor-CSE					[0] IMPLICIT Ext-SS-InfoFor-CSE OPTIONAL,
	camel-SubscriptionInfo			[1] IMPLICIT CAMEL-SubscriptionInfo OPTIONAL,
	extensionContainer				[2] IMPLICIT ExtensionContainer OPTIONAL,
	odb-Info						[3] IMPLICIT ODB-Info OPTIONAL }

ModificationRequestFor-CF-Info ::= SEQUENCE {
	ss-Code							[0] IMPLICIT SS-Code,
	basicService					[1] IMPLICIT Ext-BasicServiceCode OPTIONAL,
	ss-Status						[2] IMPLICIT Ext-SS-Status OPTIONAL,
	forwardedToNumber				[3] IMPLICIT AddressString OPTIONAL,
	forwardedToSubaddress			[4] IMPLICIT ISDN-SubaddressString OPTIONAL,
	noReplyConditionTime			[5] IMPLICIT Ext-NoRepCondTime OPTIONAL,
	modifyNotificationToCSE			[6] IMPLICIT ModificationInstruction OPTIONAL,
	extensionContainer				[7] IMPLICIT ExtensionContainer OPTIONAL
  }

ModificationRequestFor-CB-Info ::= SEQUENCE {
	ss-Code							[0] IMPLICIT SS-Code,
	basicService					[1] IMPLICIT Ext-BasicServiceCode OPTIONAL,
	ss-Status						[2] IMPLICIT Ext-SS-Status OPTIONAL,
	password						[3] IMPLICIT Password OPTIONAL,
	wrongPasswordAttemptsCounter	[4] IMPLICIT WrongPasswordAttemptsCounter OPTIONAL,
	modifyNotificationToCSE			[5] IMPLICIT ModificationInstruction OPTIONAL,
	extensionContainer				[6] IMPLICIT ExtensionContainer OPTIONAL
  }

ModificationRequestFor-ODB-data ::= SEQUENCE {
	odb-data						[0] IMPLICIT ODB-Data OPTIONAL,
	modifyNotificationToCSE			[1] IMPLICIT ModificationInstruction OPTIONAL,
	extensionContainer				[2] IMPLICIT ExtensionContainer OPTIONAL
  }

ModificationRequestFor-CSI ::= SEQUENCE {
	requestedCamel-SubscriptionInfo [0] IMPLICIT RequestedCAMEL-SubscriptionInfo,
	modifyNotificationToCSE			[1] IMPLICIT ModificationInstruction OPTIONAL,
	modifyCSI-State					[2] IMPLICIT ModificationInstruction OPTIONAL,
	extensionContainer				[3] IMPLICIT ExtensionContainer OPTIONAL,
	additionalRequestedCAMEL-SubscriptionInfo
									[4] AdditionalRequestedCAMEL-SubscriptionInfo
	OPTIONAL }
-- requestedCamel-SubscriptionInfo shall be discarded if
-- additionalRequestedCAMEL-SubscriptionInfo is received

ModificationInstruction ::= ENUMERATED {
	deactivate (0),
	activate (1)}

Ext-SS-InfoFor-CSE ::= CHOICE {
	forwardingInfoFor-CSE				[0] IMPLICIT Ext-ForwardingInfoFor-CSE,
	callBarringInfoFor-CSE				[1] IMPLICIT Ext-CallBarringInfoFor-CSE
}
NoteSubscriberDataModifiedArg ::= SEQUENCE {
      imsi								IMSI,
      msisdn							ISDN-AddressString,
      forwardingInfoFor-CSE				[0] IMPLICIT Ext-ForwardingInfoFor-CSE OPTIONAL,
      callBarringInfoFor-CSE			[1] IMPLICIT Ext-CallBarringInfoFor-CSE OPTIONAL,
      odb-Info							[2] IMPLICIT ODB-Info OPTIONAL,
      camel-SubscriptionInfo			[3] IMPLICIT CAMEL-SubscriptionInfo OPTIONAL,
      allInformationSent				[4] NULL OPTIONAL,
      extensionContainer				ExtensionContainer OPTIONAL
      }


NoteSubscriberDataModifiedRes ::= SEQUENCE {
	extensionContainer	ExtensionContainer OPTIONAL
  }

NoteMM-EventArg::= SEQUENCE {
	serviceKey						ServiceKey,
	eventMet						[0] IMPLICIT MM-Code,
	imsi							[1] IMPLICIT IMSI,
	msisdn							[2] IMPLICIT ISDN-AddressString,
	locationInformation				[3] IMPLICIT LocationInformation OPTIONAL,
	supportedCAMELPhases			[5] IMPLICIT SupportedCamelPhases OPTIONAL,
	extensionContainer				[6] IMPLICIT ExtensionContainer OPTIONAL,
	locationInformationGPRS			[7] LocationInformationGPRS OPTIONAL,
	offeredCamel4Functionalities	[8] OfferedCamel4Functionalities OPTIONAL
}

NoteMM-EventRes ::= SEQUENCE {
	extensionContainer	ExtensionContainer OPTIONAL
  }

CAMEL-SubscriptionInfo ::= SEQUENCE {
      o-CSI								[0] IMPLICIT O-CSI OPTIONAL,
      o-BcsmCamelTDP-CriteriaList		[1] IMPLICIT O-BcsmCamelTDPCriteriaList OPTIONAL,
      d-CSI								[2] IMPLICIT D-CSI OPTIONAL,
      t-CSI								[3] IMPLICIT T-CSI OPTIONAL,
      t-BCSM-CAMEL-TDP-CriteriaList		[4] IMPLICIT T-BCSM-CAMEL-TDP-CriteriaList OPTIONAL,
      vt-CSI							[5] IMPLICIT T-CSI OPTIONAL,
      vt-BCSM-CAMEL-TDP-CriteriaList	[6] IMPLICIT T-BCSM-CAMEL-TDP-CriteriaList OPTIONAL,
      tif-CSI							[7] IMPLICIT NULL OPTIONAL,
      tif-CSI-NotificationToCSE			[8] IMPLICIT NULL OPTIONAL,
      gprs-CSI							[9] IMPLICIT GPRS-CSI OPTIONAL,
      mo-sms-CSI						[10] IMPLICIT SMS-CSI OPTIONAL,
      ss-CSI							[11] IMPLICIT SS-CSI OPTIONAL,
      m-CSI								[12] IMPLICIT M-CSI OPTIONAL,
      extensionContainer				[13] IMPLICIT ExtensionContainer OPTIONAL,
      specificCSIDeletedList			[14] IMPLICIT SpecificCSI-Withdraw OPTIONAL,
      mt-sms-CSI						[15] IMPLICIT SMS-CSI OPTIONAL,
      mt-smsCAMELTDP-CriteriaList		[16] IMPLICIT MT-smsCAMELTDP-CriteriaList OPTIONAL,
      mg-csi							[17] IMPLICIT MG-CSI OPTIONAL,
      o-IM-CSI							[18] IMPLICIT O-CSI OPTIONAL,
      o-IM-BcsmCamelTDP-CriteriaList	[19] IMPLICIT O-BcsmCamelTDPCriteriaList OPTIONAL,
      d-IM-CSI							[20] IMPLICIT D-CSI OPTIONAL,
      vt-IM-CSI							[21] IMPLICIT T-CSI OPTIONAL,
      vt-IM-BCSM-CAMEL-TDP-CriteriaList [22] IMPLICIT T-BCSM-CAMEL-TDP-CriteriaList OPTIONAL
}

Ext-ForwardingInfoFor-CSE ::= SEQUENCE {
      ss-Code				[0] IMPLICIT SS-Code,
      forwardingFeatureList [1] IMPLICIT Ext-ForwFeatureList,
      notificationToCSE		[2] IMPLICIT NULL OPTIONAL,
      extensionContainer	[3] IMPLICIT ExtensionContainer OPTIONAL
      }



Ext-SS-Status ::= OCTET STRING (SIZE (1..5))
-- OCTET 1:
--
-- bits 8765: 0000 (unused)
-- bits 4321: Used to convey the "P bit","R bit","A bit" and "Q bit",
-- representing supplementary service state information
-- as defined in TS 3GPP TS 23.011 [22]
-- bit 4: "Q bit"
-- bit 3: "P bit"
-- bit 2: "R bit"
-- bit 1: "A bit"
-- OCTETS 2-5: reserved for future use. They shall be discarded if
-- received and not understood.

AgeOfLocationInformation ::= INTEGER (0..32767)
-- the value represents the elapsed time in minutes since the last
-- network contact of the mobile station (i.e. the actuality of the
-- location information).
-- value '0' indicates that the MS is currently in contact with the
-- network
-- value '32767' indicates that the location information is at least
-- 32767 minutes old

Ext-BasicServiceCode ::= CHOICE {
	ext-BearerService	[2] IMPLICIT Ext-BearerServiceCode,
	ext-Teleservice		[3] IMPLICIT Ext-TeleserviceCode}

Ext-BearerServiceCode ::= OCTET STRING (SIZE (1..5))
-- This type is used to represent the code identifying a single
-- bearer service, a group of bearer services, or all bearer
-- services. The services are defined in TS 3GPP TS 22.002 [3].
-- The internal structure is defined as follows:
--
-- OCTET 1:
-- plmn-specific bearer services:
-- bits 87654321: defined by the HPLMN operator
--
-- rest of bearer services:
-- bit 8: 0 (unused)
-- bits 7654321: group (bits 7654), and rate, if applicable
-- (bits 321)
-- OCTETS 2-5: reserved for future use. If received the
-- Ext-TeleserviceCode shall be
-- treated according to the exception handling defined for the
-- operation that uses this type.
-- Ext-BearerServiceCode includes all values defined for BearerServiceCode.

Ext-TeleserviceCode ::= OCTET STRING (SIZE (1..5))
-- This type is used to represent the code identifying a single
-- teleservice, a group of teleservices, or all teleservices. The
-- services are defined in TS GSM 22.003 [4].
-- The internal structure is defined as follows:
-- OCTET 1:
-- bits 87654321: group (bits 8765) and specific service
-- (bits 4321)
-- OCTETS 2-5: reserved for future use. If received the
-- Ext-TeleserviceCode shall be
-- treated according to the exception handling defined for the
-- operation that uses this type.
-- Ext-TeleserviceCode includes all values defined for TeleserviceCode.

FTN-AddressString ::=
AddressString (SIZE (1..15))
-- This type is used to represent forwarded-to numbers.
-- For long forwarded-to numbers (longer than 15 digits) NPI shall be unknown;
-- if NAI = international the first digits represent the country code (CC)
-- and the network destination code (NDC) as for E.164.

AddressString ::= OCTET STRING (SIZE (1..20))
-- This type is used to represent a number for addressing
-- purposes. It is composed of
-- a) one octet for nature of address, and numbering plan
-- indicator.
-- b) digits of an address encoded as TBCD-String.
-- a) The first octet includes a one bit extension indicator, a
-- 3 bits nature of address indicator and a 4 bits numbering
-- plan indicator, encoded as follows:
-- bit 8: 1 (no extension)
-- bits 765: nature of address indicator
-- 000 unknown
-- 001 international number
-- 010 national significant number
-- 011 network specific number
-- 100 subscriber number
-- 101 reserved
-- 110 abbreviated number
-- 111 reserved for extension
-- bits 4321: numbering plan indicator
-- 0000 unknown
-- 0001 ISDN/Telephony Numbering Plan (Rec ITU-T E.164)
-- 0010 spare
-- 0011 data numbering plan (ITU-T Rec X.121)
-- 0100 telex numbering plan (ITU-T Rec F.69)
-- 0101 spare
-- 0110 land mobile numbering plan (ITU-T Rec E.212)
-- 0111 spare
-- 1000 national numbering plan
-- 1001 private numbering plan
-- 1111 reserved for extension
-- all other values are reserved.
-- b) The following octets representing digits of an address
-- encoded as a TBCD-STRING.


ISDN-SubaddressString ::= OCTET STRING (SIZE (1..21))
-- This type is used to represent ISDN subaddresses.
-- It is composed of
-- a) one octet for type of subaddress and odd/even indicator.
-- b) 20 octets for subaddress information.
-- a) The first octet includes a one bit extension indicator, a
-- 3 bits type of subaddress and a one bit odd/even indicator,
-- encoded as follows:
-- bit 8: 1 (no extension)
-- bits 765: type of subaddress
-- 000 NSAP (X.213/ISO 8348 AD2)
-- 010 User Specified
-- All other values are reserved
-- bit 4: odd/even indicator
-- 0 even number of address signals
-- 1 odd number of address signals
-- The odd/even indicator is used when the type of subaddress
-- is "user specified" and the coding is BCD.
-- bits 321: 000 (unused)
-- b) Subaddress information.
-- The NSAP X.213/ISO8348AD2 address shall be formatted as specified
-- by octet 4 which contains the Authority and Format Identifier
-- (AFI). The encoding is made according to the "preferred binary
-- encoding" as defined in X.213/ISO834AD2. For the definition
-- of this type of subaddress, see ITU-T Rec I.334.
-- For User-specific subaddress, this field is encoded according
-- to the user specification, subject to a maximum length of 20
-- octets. When interworking with X.25 networks BCD coding should
-- be applied.

Ext-CallBarringInfoFor-CSE ::= SEQUENCE {
	ss-Code							[0] IMPLICIT SS-Code,
	callBarringFeatureList			[1] IMPLICIT Ext-CallBarFeatureList,
	password						[2] IMPLICIT Password OPTIONAL,
	wrongPasswordAttemptsCounter	[3] IMPLICIT WrongPasswordAttemptsCounter OPTIONAL,
	notificationToCSE				[4] IMPLICIT NULL OPTIONAL,
	extensionContainer				[5] IMPLICIT ExtensionContainer OPTIONAL
  }

ODB-Info ::= SEQUENCE {
	odb-Data			ODB-Data,
	notificationToCSE	NULL OPTIONAL,
	extensionContainer	ExtensionContainer OPTIONAL
  }

ODB-Data ::= SEQUENCE {
	odb-GeneralData			ODB-GeneralData,
	odb-HPLMN-Data			ODB-HPLMN-Data OPTIONAL,
	extensionContainer		ExtensionContainer OPTIONAL
  }

ModifyNotificationToCSE ::= ENUMERATED {
            deactivate    (0 ), 
            activate      (1 )}


M-CSI ::= SEQUENCE {
	mobilityTriggers		MobilityTriggers,
	serviceKey				ServiceKey,
	gsmSCF-Address			[0] IMPLICIT ISDN-AddressString,
	extensionContainer		[1] IMPLICIT ExtensionContainer OPTIONAL,
	notificationToCSE		[2] IMPLICIT NULL OPTIONAL,
	csi-Active				[3] IMPLICIT NULL OPTIONAL
  }
-- notificationToCSE and csi-Active shall not be present when M-CSI is sent to VLR.
-- They may only be included in ATSI/ATM ack/NSDC message.		




SS-EventList ::= SEQUENCE SIZE (1..10) OF SS-Code
-- Actions for the following SS-Code values are defined in CAMEL Phase 3:
-- ect SS-Code ::= '00110001'B
-- multiPTY SS-Code ::= '01010001'B
-- cd SS-Code ::= '00100100'B
-- ccbs SS-Code ::= '01000100'B
-- all other SS codes shall be ignored
-- When SS-CSI is sent to the VLR, it shall not contain a marking for ccbs.
-- If the VLR receives SS-CSI containing a marking for ccbs, the VLR shall discard the
-- ccbs marking in SS-CSI.

T-CSI ::= SEQUENCE {
	t-BcsmCamelTDPDataList		T-BcsmCamelTDPDataList,
	extensionContainer			ExtensionContainer OPTIONAL,
	camelCapabilityHandling		[0] IMPLICIT CamelCapabilityHandling OPTIONAL,
	notificationToCSE			[1] IMPLICIT NULL OPTIONAL,
	csi-Active					[2] IMPLICIT NULL OPTIONAL}
-- notificationToCSE and csi-Active shall not be present when VT-CSI/T-CSI is sent
-- to VLR/GMSC.
-- They may only be included in ATSI/ATM ack/NSDC message.
-- T-CSI shall not be segmented.

T-BcsmCamelTDPDataList ::= SEQUENCE SIZE (1..10) OF
T-BcsmCamelTDPData
--- T-BcsmCamelTDPDataList shall not contain more than one instance of
--- T-BcsmCamelTDPData containing the same value for t-BcsmTriggerDetectionPoint.
--- For CAMEL Phase 2, this means that only one instance of T-BcsmCamelTDPData is allowed
--- with t-BcsmTriggerDetectionPoint being equal to DP12.
--- For CAMEL Phase 3, more TDP"s are allowed.

T-BcsmCamelTDPData ::= SEQUENCE {
	t-BcsmTriggerDetectionPoint		T-BcsmTriggerDetectionPoint,
	serviceKey						ServiceKey,
	gsmSCF-Address					[0] IMPLICIT ISDN-AddressString,
	defaultCallHandling				[1] IMPLICIT DefaultCallHandling,
	extensionContainer				[2] IMPLICIT ExtensionContainer OPTIONAL
  }


SMS-CSI ::= SEQUENCE {
	sms-CAMEL-TDP-DataList		[0] IMPLICIT SMS-CAMEL-TDP-DataList OPTIONAL,
	camelCapabilityHandling		[1] IMPLICIT CamelCapabilityHandling OPTIONAL,
	extensionContainer			[2] IMPLICIT ExtensionContainer OPTIONAL,
	notificationToCSE			[3] IMPLICIT NULL OPTIONAL,
	csi-Active					[4] IMPLICIT NULL OPTIONAL
  }
-- notificationToCSE and csi-Active shall not be present
-- when MO-SMS-CSI or MT-SMS-CSI is sent to VLR or SGSN.
-- They may only be included in ATSI/ATM ack/NSDC message.
-- SMS-CAMEL-TDP-Data and camelCapabilityHandling shall be present in
-- the SMS-CSI sequence.
-- If SMS-CSI is segmented, sms-CAMEL-TDP-DataList and camelCapabilityHandling shall be
-- present in the first segment

SMS-CAMEL-TDP-DataList ::= SEQUENCE SIZE (1..10) OF
SMS-CAMEL-TDP-Data
-- SMS-CAMEL-TDP-DataList shall not contain more than one instance of
-- SMS-CAMEL-TDP-Data containing the same value for sms-TriggerDetectionPoint.

SMS-CAMEL-TDP-Data ::= SEQUENCE {
	sms-TriggerDetectionPoint	[0] IMPLICIT SMS-TriggerDetectionPoint,
	serviceKey					[1] IMPLICIT ServiceKey,
	gsmSCF-Address				[2] ISDN-AddressString,
	defaultSMS-Handling			[3] IMPLICIT DefaultSMS-Handling,
	extensionContainer			[4] IMPLICIT ExtensionContainer OPTIONAL
}

SMS-TriggerDetectionPoint ::= ENUMERATED {
	sms-CollectedInfo (1),
	sms-DeliveryRequest (2)
}
-- exception handling:
-- For SMS-CAMEL-TDP-Data and MT-smsCAMELTDP-Criteria sequences containing this
-- parameter with any other value than the ones listed the receiver shall ignore
-- the whole sequence.
--
-- If this parameter is received with any other value than sms-CollectedInfo
-- in an SMS-CAMEL-TDP-Data sequence contained in mo-sms-CSI, then the receiver shall
-- ignore the whole SMS-CAMEL-TDP-Data sequence.
--
-- If this parameter is received with any other value than sms-DeliveryRequest
-- in an SMS-CAMEL-TDP-Data sequence contained in mt-sms-CSI then the receiver shall
-- ignore the whole SMS-CAMEL-TDP-Data sequence.
--
-- If this parameter is received with any other value than sms-DeliveryRequest
-- in an MT-smsCAMELTDP-Criteria sequence then the receiver shall
-- ignore the whole MT-smsCAMELTDP-Criteria sequence.

DefaultSMS-Handling ::= ENUMERATED {
	continueTransaction (0) ,
	releaseTransaction (1)
  }
-- exception handling:
-- reception of values in range 2-31 shall be treated as "continueTransaction"
-- reception of values greater than 31 shall be treated as "releaseTransaction"

CamelCapabilityHandling ::= INTEGER(1..16)
-- value 1 = CAMEL phase 1,
-- value 2 = CAMEL phase 2,
-- value 3 = CAMEL Phase 3,
-- value 4 = CAMEL phase 4:
-- reception of values greater than 4 shall be treated as CAMEL phase 4.



MobilityTriggers ::= SEQUENCE SIZE (1..10) OF
MM-Code

MM-Code ::= OCTET STRING (SIZE (1))

-- This type is used to indicate a Mobility Management event.
-- Actions for the following MM-Code values are defined in CAMEL Phase 4:
--
-- CS domain MM events:
-- Location-update-in-same-VLR MM-Code ::= '00000000'B
-- Location-update-to-other-VLR MM-Code ::= '00000001'B
-- IMSI-Attach MM-Code ::= '00000010'B
-- MS-initiated-IMSI-Detach MM-Code ::= '00000011'B
-- Network-initiated-IMSI-Detach MM-Code ::= '00000100'B
--
-- PS domain MM events:
-- Routeing-Area-update-in-same-SGSN MM-Code ::= '10000000'B
-- Routeing-Area-update-to-other-SGSN-update-from-new-SGSN
-- MM-Code ::= '10000001'B
-- Routeing-Area-update-to-other-SGSN-disconnect-by-detach
-- MM-Code ::= '10000010'B
-- GPRS-Attach MM-Code ::= '10000011'B
-- MS-initiated-GPRS-Detach MM-Code ::= '10000100'B
-- Network-initiated-GPRS-Detach MM-Code ::= '10000101'B
-- Network-initiated-transfer-to-MS-not-reachable-for-paging
-- MM-Code ::= '10000110'B
--
-- If the MSC receives any other MM-code than the ones listed above for the
-- CS domain, then the MSC shall ignore that MM-code.
-- If the SGSN receives any other MM-code than the ones listed above for the
-- PS domain, then the SGSN shall ignore that MM-code.



--   ERRORS     {
--      atm-NotAllowed | 
--      dataMissing | 
--      unexpectedDataValue | 
--      unknownSubscriber | 
--      bearerServiceNotProvisioned | 
--      teleserviceNotProvisioned | 
--      callBarred | 
--      illegalSS-Operation | 
--      ss-SubscriptionViolation | 
--      ss-ErrorStatus | 
--      ss-Incompatibility | 
--      informationNotAvailable }
--   CODE     local      : 65
--   }

--ss-InvocationNotification OPERATION
--   ARGUMENT
Ss-InvocationNotificationArg ::= SEQUENCE {
         imsi                    [0] IMPLICIT IMSI, 
         msisdn                  [1] IMPLICIT ISDN-AddressString, 
         ss-Event                [2] IMPLICIT OCTET STRING ( SIZE( 1 ) ), 
         ss-EventSpecification   [3] IMPLICIT SEQUENCE SIZE( 1 .. 2 ) OF
            OCTET STRING ( SIZE( 1 .. 20 ) ) OPTIONAL, 
         extensionContainer      [4] IMPLICIT ExtensionContainer OPTIONAL
         }
--   RESULT
Ss-InvocationNotificationRes ::= SEQUENCE {
         extensionContainer   ExtensionContainer OPTIONAL
         }
--   ERRORS {
-- dataMissing   localValue : 35, 
-- unexpectedDataValue   localValue : 36, 
-- unknownSubscriber   localValue : 1}
-- ::= localValue : 72

--prepareGroupCall OPERATION
--   ARGUMENT

PrepareGroupCallArg ::= SEQUENCE {
	teleservice					Ext-TeleserviceCode,
	asciCallReference			ASCI-CallReference,
	codec-Info					CODEC-Info,
	cipheringAlgorithm			CipheringAlgorithm,
	groupKeyNumber-Vk-Id		[0] IMPLICIT GroupKeyNumber OPTIONAL,
	groupKey					[1] IMPLICIT Kc OPTIONAL,
-- this parameter shall not be sent and shall be discarded if received
	priority					[2] IMPLICIT EMLPP-Priority OPTIONAL,
	uplinkFree					[3] IMPLICIT NULL OPTIONAL,
	extensionContainer			[4] IMPLICIT ExtensionContainer OPTIONAL,
	vstk						[5] IMPLICIT VSTK OPTIONAL,
	vstk-rand					[6] IMPLICIT VSTK-RAND OPTIONAL }
--   RESULT

VSTK ::= OCTET STRING (SIZE (16))

VSTK-RAND ::= OCTET STRING (SIZE (5))
-- The 36 bit value is carried in bit 7 of octet 1 to bit 4 of octet 5
-- bits 3, 2, 1, and 0 of octet 5 are padded with zeros.

CODEC-Info ::= OCTET STRING (SIZE (5..10))
-- Refers to channel type
-- coded according to 3GPP TS 48.008 [49] and including Element identifier and Length

CipheringAlgorithm ::= OCTET STRING (SIZE (1))
-- Refers to 'permitted algorithms' in 'encryption information'
-- coded according to 3GPP TS 48.008 [49]:
-- Bits 8-1
-- 8765 4321
-- 0000 0001 No encryption
-- 0000 0010 GSM A5/1
-- 0000 0100 GSM A5/2
-- 0000 1000 GSM A5/3
-- 0001 0000 GSM A5/4
-- 0010 0000 GSM A5/5
-- 0100 0000 GSM A5/6
-- 1000 0000 GSM A5/7

PrepareGroupCallRes ::= SEQUENCE {
         groupCallNumber      ISDN-AddressString, 
         extensionContainer   ExtensionContainer OPTIONAL
         }
--   ERRORS {
-- systemFailure   localValue : 34, 
-- noGroupCallNumberAvailable   localValue : 50, 
-- unexpectedDataValue   localValue : 36}
-- ::= localValue : 39

--sendGroupCallEndSignal OPERATION
--   ARGUMENT
SendGroupCallEndSignalArg ::= SEQUENCE {
         imsi                 IMSI OPTIONAL, 
         extensionContainer   ExtensionContainer OPTIONAL
         }
--   RESULT
SendGroupCallEndSignalRes ::= SEQUENCE {
         extensionContainer   ExtensionContainer OPTIONAL
         }
-- ::= localValue : 40

--processGroupCallSignalling OPERATION
--   ARGUMENT
ProcessGroupCallSignallingArg ::= SEQUENCE {
         uplinkRequest             [0] IMPLICIT NULL OPTIONAL, 
         uplinkReleaseIndication   [1] IMPLICIT NULL OPTIONAL, 
         releaseGroupCall          [2] IMPLICIT NULL OPTIONAL, 
         extensionContainer        ExtensionContainer OPTIONAL
         }
-- ::= localValue : 41

GroupKeyNumber ::= INTEGER (0..15)

--forwardGroupCallSignalling OPERATION
--   ARGUMENT
ForwardGroupCallSignallingArg ::= SEQUENCE {
         imsi                      IMSI OPTIONAL, 
         uplinkRequestAck          [0] IMPLICIT NULL OPTIONAL, 
         uplinkReleaseIndication   [1] IMPLICIT NULL OPTIONAL, 
         uplinkRejectCommand       [2] IMPLICIT NULL OPTIONAL, 
         uplinkSeizedCommand       [3] IMPLICIT NULL OPTIONAL, 
         uplinkReleaseCommand      [4] IMPLICIT NULL OPTIONAL, 
         extensionContainer        ExtensionContainer OPTIONAL
         }
-- ::= localValue : 42

--updateGprsLocation OPERATION
--   ARGUMENT

UpdateGprsLocationArg ::= SEQUENCE {
	imsi							IMSI,
	sgsn-Number						ISDN-AddressString,
	sgsn-Address					GSN-Address,
	extensionContainer				ExtensionContainer OPTIONAL,
	sgsn-Capability					[0] IMPLICIT SGSN-Capability OPTIONAL,
	informPreviousNetworkEntity		[1] IMPLICIT NULL OPTIONAL,
	ps-LCS-NotSupportedByUE			[2] IMPLICIT NULL OPTIONAL,
	v-gmlc-Address					[3] IMPLICIT GSN-Address OPTIONAL,
	add-info						[4] IMPLICIT ADD-Info OPTIONAL }

--   RESULT
UpdateGprsLocationRes ::= SEQUENCE {
	hlr-Number				ISDN-AddressString,
	extensionContainer		ExtensionContainer OPTIONAL,
	add-Capability			NULL OPTIONAL }

--   ERRORS {
-- systemFailure   localValue : 34, 
-- unexpectedDataValue   localValue : 36, 
-- unknownSubscriber   localValue : 1, 
-- roamingNotAllowed   localValue : 8}
-- ::= localValue : 23

SGSN-Capability ::= SEQUENCE{
	solsaSupportIndicator							NULL OPTIONAL,
	extensionContainer								[1] IMPLICIT ExtensionContainer OPTIONAL,
	superChargerSupportedInServingNetworkEntity		[2] IMPLICIT SuperChargerInfo OPTIONAL ,
	gprsEnhancementsSupportIndicator				[3] IMPLICIT NULL OPTIONAL,
	supportedCamelPhases							[4] IMPLICIT SupportedCamelPhases OPTIONAL,
	supportedLCS-CapabilitySets						[5] IMPLICIT SupportedLCS-CapabilitySets OPTIONAL,
	offeredCamel4CSIs								[6] IMPLICIT OfferedCamel4CSIs OPTIONAL,
	smsCallBarringSupportIndicator					[7] IMPLICIT NULL OPTIONAL }

GSN-Address ::= OCTET STRING (SIZE (5..17))
-- Octets are coded according to TS 3GPP TS 23.003 [17]


--sendRoutingInfoForGprs OPERATION
--   ARGUMENT
SendRoutingInfoForGprsArg ::= SEQUENCE {
         imsi                 [0] IMPLICIT IMSI, 
         ggsn-Address         [1] IMPLICIT GSN-Address OPTIONAL, 
         ggsn-Number          [2] IMPLICIT ISDN-AddressString, 
         extensionContainer   [3] IMPLICIT ExtensionContainer OPTIONAL
         }
--   RESULT

SendRoutingInfoForGprsRes ::= SEQUENCE {
	sgsn-Address				[0] IMPLICIT GSN-Address,
	ggsn-Address				[1] IMPLICIT GSN-Address OPTIONAL,
	mobileNotReachableReason	[2] IMPLICIT AbsentSubscriberDiagnosticSM OPTIONAL,
	extensionContainer			[3] IMPLICIT ExtensionContainer OPTIONAL
  }
--   ERRORS {
-- absentSubscriber   localValue : 27, 
-- systemFailure   localValue : 34, 
-- dataMissing   localValue : 35, 
-- unexpectedDataValue   localValue : 36, 
-- unknownSubscriber   localValue : 1}
-- ::= localValue : 24

--failureReport OPERATION
--   ARGUMENT
FailureReportArg ::= SEQUENCE {
         imsi                 [0] IMPLICIT IMSI, 
         ggsn-Number          [1] IMPLICIT ISDN-AddressString, 
         ggsn-Address         [2] IMPLICIT GSN-Address OPTIONAL, 
         extensionContainer   [3] IMPLICIT ExtensionContainer OPTIONAL
         }
--   RESULT
FailureReportRes ::= SEQUENCE {
         ggsn-Address         [0] IMPLICIT GSN-Address OPTIONAL, 
         extensionContainer   [1] IMPLICIT ExtensionContainer OPTIONAL
         }

--   ERRORS {
-- systemFailure   localValue : 34, 
-- dataMissing   localValue : 35, 
-- unexpectedDataValue   localValue : 36, 
-- unknownSubscriber   localValue : 1}
-- ::= localValue : 25

--noteMsPresentForGprs OPERATION
--   ARGUMENT

NoteMsPresentForGprsArg ::= SEQUENCE {
	imsi				[0] IMPLICIT IMSI,
	sgsn-Address		[1] IMPLICIT GSN-Address,
	ggsn-Address		[2] IMPLICIT GSN-Address OPTIONAL,
	extensionContainer	[3] IMPLICIT ExtensionContainer OPTIONAL
  }
--   RESULT
NoteMsPresentForGprsRes ::= SEQUENCE {
         extensionContainer   [0] IMPLICIT ExtensionContainer OPTIONAL
         }
--   ERRORS {
-- systemFailure   localValue : 34, 
-- dataMissing   localValue : 35, 
-- unexpectedDataValue   localValue : 36, 
-- unknownSubscriber   localValue : 1}
-- ::= localValue : 26



--provideSubscriberLocation OPERATION
--   ARGUMENT

ProvideSubscriberLocation-Arg ::= SEQUENCE {
	locationType				LocationType,
	mlc-Number					ISDN-AddressString,
	lcs-ClientID				[0] IMPLICIT LCS-ClientID OPTIONAL,
	privacyOverride				[1] IMPLICIT NULL OPTIONAL,
	imsi						[2] IMPLICIT IMSI OPTIONAL,
	msisdn						[3] IMPLICIT ISDN-AddressString OPTIONAL,
	lmsi						[4] IMPLICIT LMSI OPTIONAL,
	imei						[5] IMPLICIT IMEI OPTIONAL,
	lcs-Priority				[6] IMPLICIT LCS-Priority OPTIONAL,
	lcs-QoS						[7] IMPLICIT LCS-QoS OPTIONAL,
	extensionContainer			[8] IMPLICIT ExtensionContainer OPTIONAL,
	supportedGADShapes			[9] IMPLICIT SupportedGADShapes OPTIONAL,
	lcs-ReferenceNumber			[10] IMPLICIT LCS-ReferenceNumber OPTIONAL,
	lcsServiceTypeID			[11] IMPLICIT LCSServiceTypeID OPTIONAL,
	lcsCodeword					[12] IMPLICIT LCSCodeword OPTIONAL,
	lcs-PrivacyCheck			[13] IMPLICIT LCS-PrivacyCheck OPTIONAL,
	areaEventInfo				[14] IMPLICIT AreaEventInfo OPTIONAL,
	h-gmlc-Address				[15] IMPLICIT GSN-Address OPTIONAL }

-- one of imsi or msisdn is mandatory
-- If a location estimate type indicates activate deferred location or cancel deferred
-- location, a lcs-Reference number shall be included.

LocationType ::= SEQUENCE {
	locationEstimateType		[0] IMPLICIT LocationEstimateType,
	deferredLocationEventType	[1] IMPLICIT DeferredLocationEventType OPTIONAL }

LocationEstimateType ::= ENUMERATED {
	currentLocation (0),
	currentOrLastKnownLocation (1),
	initialLocation (2),
	activateDeferredLocation (3),
	cancelDeferredLocation (4) }
-- exception handling:
-- a ProvideSubscriberLocation-Arg containing an unrecognized LocationEstimateType
-- shall be rejected by the receiver with a return error cause of unexpected data value

DeferredLocationEventType ::= BIT STRING {
	msAvailable (0) ,
	enteringIntoArea (1),
	leavingFromArea (2),
	beingInsideArea (3) } (SIZE (1..16))
-- beingInsideArea is always treated as oneTimeEvent regardless of the possible value
-- of occurrenceInfo inside areaEventInfo.
-- exception handling:
-- a ProvideSubscriberLocation-Arg containing other values than listed above in
-- DeferredLocationEventType shall be rejected by the receiver with a return error cause of
-- unexpected data value.

LCS-ClientID ::= SEQUENCE {
	lcsClientType		[0] IMPLICIT LCSClientType,
	lcsClientExternalID [1] IMPLICIT LCSClientExternalID OPTIONAL,
	lcsClientDialedByMS [2] IMPLICIT AddressString OPTIONAL,
	lcsClientInternalID [3] IMPLICIT LCSClientInternalID OPTIONAL,
	lcsClientName		[4] IMPLICIT LCSClientName OPTIONAL,
	lcsAPN				[5] IMPLICIT APN OPTIONAL,
	lcsRequestorID		[6] IMPLICIT LCSRequestorID OPTIONAL }

LCSClientType ::= ENUMERATED {
	emergencyServices (0),
	valueAddedServices (1),
	plmnOperatorServices (2),
	lawfulInterceptServices (3)
  }
-- exception handling:
-- unrecognized values may be ignored if the LCS client uses the privacy override
-- otherwise, an unrecognized value shall be treated as unexpected data by a receiver
-- a return error shall then be returned if received in a MAP invoke

LCSClientName ::= SEQUENCE {
	dataCodingScheme	[0] IMPLICIT USSD-DataCodingScheme,
	nameString			[2] IMPLICIT NameString,
	lcs-FormatIndicator [3] IMPLICIT LCS-FormatIndicator OPTIONAL }

NameString ::= USSD-String (SIZE (1..63))

LCSRequestorID ::= SEQUENCE {
	dataCodingScheme		[0] IMPLICIT USSD-DataCodingScheme,
	requestorIDString		[1] IMPLICIT RequestorIDString,
	lcs-FormatIndicator		[2] IMPLICIT LCS-FormatIndicator OPTIONAL }

RequestorIDString ::= USSD-String (SIZE (1..63))

LCS-FormatIndicator ::= ENUMERATED {
	logicalName (0),
	e-mailAddress (1),
	msisdn (2),
	url (3),
	sipUrl (4)
  }
LCS-Priority ::= OCTET STRING (SIZE (1))
-- 0 = highest priority
-- 1 = normal priority
-- all other values treated as 1

LCS-QoS ::= SEQUENCE {
	horizontal-accuracy			[0] IMPLICIT Horizontal-Accuracy OPTIONAL,
	verticalCoordinateRequest	[1] IMPLICIT NULL OPTIONAL,
	vertical-accuracy			[2] IMPLICIT Vertical-Accuracy OPTIONAL,
	responseTime				[3] IMPLICIT ResponseTime OPTIONAL,
	extensionContainer			[4] IMPLICIT ExtensionContainer OPTIONAL
  }

Horizontal-Accuracy ::= OCTET STRING (SIZE (1))

Vertical-Accuracy ::= OCTET STRING (SIZE (1))

ResponseTime ::= SEQUENCE {
	responseTimeCategory	ResponseTimeCategory
  }
-- note: an expandable SEQUENCE simplifies later addition of a numeric response time.

ResponseTimeCategory ::= ENUMERATED {
	lowdelay (0),
	delaytolerant (1)
  }

SupportedGADShapes ::= BIT STRING {
	ellipsoidPoint (0),
	ellipsoidPointWithUncertaintyCircle (1),
	ellipsoidPointWithUncertaintyEllipse (2),
	polygon (3),
	ellipsoidPointWithAltitude (4),
	ellipsoidPointWithAltitudeAndUncertaintyElipsoid (5),
	ellipsoidArc (6) } (SIZE (7..16))
-- A node shall mark in the BIT STRING all Shapes defined in 3GPP TS 23.032 it supports.
-- exception handling: bits 7 to 15 shall be ignored if received.

LCS-ReferenceNumber::= OCTET STRING (SIZE(1))

LCSCodeword ::= SEQUENCE {
	dataCodingScheme	[0] IMPLICIT USSD-DataCodingScheme,
	lcsCodewordString	[1] IMPLICIT LCSCodewordString
  }

LCSCodewordString ::= USSD-String (SIZE (1..20))

LCS-PrivacyCheck ::= SEQUENCE {
	callSessionUnrelated	[0] IMPLICIT PrivacyCheckRelatedAction,
	callSessionRelated		[1] IMPLICIT PrivacyCheckRelatedAction OPTIONAL
  }

PrivacyCheckRelatedAction ::= ENUMERATED {
	allowedWithoutNotification (0),
	allowedWithNotification (1),
	allowedIfNoResponse (2),
	restrictedIfNoResponse (3),
	notAllowed (4)
  }
-- exception handling:
-- a ProvideSubscriberLocation-Arg containing an unrecognized PrivacyCheckRelatedAction
-- shall be rejected by the receiver with a return error cause of unexpected data value

AreaEventInfo ::= SEQUENCE {
	areaDefinition	[0] IMPLICIT AreaDefinition,
	occurrenceInfo	[1] IMPLICIT OccurrenceInfo OPTIONAL,
	intervalTime	[2] IMPLICIT IntervalTime OPTIONAL
  }
AreaDefinition ::= SEQUENCE {
	areaList [0] IMPLICIT AreaList
  }
AreaList ::= SEQUENCE SIZE (1..10) OF Area

Area ::= SEQUENCE {
	areaType			[0] IMPLICIT AreaType,
	areaIdentification	[1] IMPLICIT AreaIdentification
  }

AreaType ::= ENUMERATED {
	countryCode (0),
	plmnId (1),
	locationAreaId (2),
	routingAreaId (3),
	cellGlobalId (4)
  }

AreaIdentification ::= OCTET STRING (SIZE (2..7))
-- The internal structure is defined as follows:
-- octet 1 bits 4321 Mobile Country Code 1st digit
-- bits 8765 Mobile Country Code 2nd digit
-- octet 2 bits 4321 Mobile Country Code 3rd digit
-- bits 8765 Mobile Network Code 3rd digit if 3 digit MNC included
-- or filler (1111)
-- octet 3 bits 4321 Mobile Network Code 1st digit
-- bits 8765 Mobile Network Code 2nd digit
-- octets 4 and 5 Location Area Code (LAC)
-- octet 6 Routing Area Code (RAC) for Routing Area Id
-- octets 6 and 7 Cell Identity (CI) for Cell Global Id

OccurrenceInfo ::= ENUMERATED {
	oneTimeEvent (0),
	multipleTimeEvent (1)
  }

IntervalTime ::= INTEGER (1..32767)
-- minimum interval time between area reports in seconds

--   RESULT

ProvideSubscriberLocation-Res ::= SEQUENCE {
	locationEstimate				Ext-GeographicalInformation,
	ageOfLocationEstimate			[0] IMPLICIT AgeOfLocationInformation OPTIONAL,
	extensionContainer				[1] IMPLICIT ExtensionContainer OPTIONAL,
	add-LocationEstimate			[2] IMPLICIT Add-GeographicalInformation OPTIONAL,
	deferredmt-lrResponseIndicator	[3] IMPLICIT NULL OPTIONAL,
	geranPositioningData			[4] IMPLICIT PositioningDataInformation OPTIONAL,
	utranPositioningData			[5] IMPLICIT UtranPositioningDataInfo OPTIONAL,
	cellIdOrSai						[6] IMPLICIT CellGlobalIdOrServiceAreaIdOrLAI OPTIONAL,
	sai-Present						[7] IMPLICIT NULL OPTIONAL }
	
-- if deferredmt-lrResponseIndicator is set, locationEstimate is ignored.

-- the add-LocationEstimate parameter shall not be sent to a node that did not indicate the
-- geographic shapes supported in the ProvideSubscriberLocation-Arg
-- The locationEstimate and the add-locationEstimate parameters shall not be sent if
-- the supportedGADShapes parameter has been received in ProvideSubscriberLocation-Arg
-- and the shape encoded in locationEstimate or add-LocationEstimate is not marked
-- as supported in supportedGADShapes. In such a case ProvideSubscriberLocation
-- shall be rejected with error FacilityNotSupported with additional indication
-- shapeOfLocationEstimateNotSupported.
-- sai-Present indicates that the cellIdOrSai parameter contains a Service Area Identity.

--   ERRORS {
-- systemFailure   localValue : 34, 
-- dataMissing   localValue : 35, 
-- unexpectedDataValue   localValue : 36, 
-- facilityNotSupported   localValue : 21, 
-- unidentifiedSubscriber   localValue : 5, 
-- illegalSubscriber   localValue : 9, 
-- illegalEquipment   localValue : 12, 
-- absentSubscriber   localValue : 27, 
-- unauthorizedRequestingNetwork   localValue : 52, 
-- unauthorizedLCSClient   localValue : 53, 
-- positionMethodFailure   localValue : 54}
-- ::= localValue : 83

Ext-GeographicalInformation ::= OCTET STRING (SIZE (1..maxExt-GeographicalInformation))
-- Refers to geographical Information defined in 3GPP TS 23.032.
-- This is composed of 1 or more octets with an internal structure according to
-- 3GPP TS 23.032
-- Octet 1: Type of shape, only the following shapes in 3GPP TS 23.032 are allowed:
-- (a) Ellipsoid point with uncertainty circle
-- (b) Ellipsoid point with uncertainty ellipse
-- (c) Ellipsoid point with altitude and uncertainty ellipsoid
-- (d) Ellipsoid Arc
-- (e) Ellipsoid Point
-- Any other value in octet 1 shall be treated as invalid
-- Octets 2 to 8 for case (a) - Ellipsoid point with uncertainty circle
-- Degrees of Latitude 3 octets
-- Degrees of Longitude 3 octets
-- Uncertainty code 1 octet
-- Octets 2 to 11 for case (b) - Ellipsoid point with uncertainty ellipse:
-- Degrees of Latitude 3 octets
-- Degrees of Longitude 3 octets
-- Uncertainty semi-major axis 1 octet
-- Uncertainty semi-minor axis 1 octet
-- Angle of major axis 1 octet
-- Confidence 1 octet
-- Octets 2 to 14 for case (c) - Ellipsoid point with altitude and uncertainty ellipsoid
-- Degrees of Latitude 3 octets
-- Degrees of Longitude 3 octets
-- Altitude 2 octets
-- Uncertainty semi-major axis 1 octet
-- Uncertainty semi-minor axis 1 octet
-- Angle of major axis 1 octet
-- Uncertainty altitude 1 octet
-- Confidence 1 octet
-- Octets 2 to 13 for case (d) - Ellipsoid Arc
-- Degrees of Latitude 3 octets
-- Degrees of Longitude 3 octets
-- Inner radius 2 octets
-- Uncertainty radius 1 octet
-- Offset angle 1 octet
-- Included angle 1 octet
-- Confidence 1 octet
-- Octets 2 to 7 for case (e) - Ellipsoid Point
-- Degrees of Latitude 3 octets
-- Degrees of Longitude 3 octets

--
-- An Ext-GeographicalInformation parameter comprising more than one octet and
-- containing any other shape or an incorrect number of octets or coding according
-- to 3GPP TS 23.032 shall be treated as invalid data by a receiver.
--
-- An Ext-GeographicalInformation parameter comprising one octet shall be discarded
-- by the receiver if an Add-GeographicalInformation parameter is received
-- in the same message.
--
-- An Ext-GeographicalInformation parameter comprising one octet shall be treated as
-- invalid data by the receiver if an Add-GeographicalInformation parameter is not
-- received in the same message.

maxExt-GeographicalInformation INTEGER ::= 20
-- the maximum length allows for further shapes in 3GPP TS 23.032 to be included in later
-- versions of 3GPP TS 29.002

PositioningDataInformation ::= OCTET STRING (SIZE (2..10))
-- Refers to the Positioning Data defined in 3GPP TS 49.031.
-- This is composed of 2 or more octets with an internal structure according to
-- 3GPP TS 49.031.

maxPositioningDataInformation INTEGER ::= 10


UtranPositioningDataInfo ::= OCTET STRING (SIZE (3..10))
-- Refers to the Position Data defined in 3GPP TS 25.413.
-- This is composed of the positioningDataDiscriminator and the positioningDataSet
-- included in positionData as defined in 3GPP TS 25.413.

Add-GeographicalInformation ::= OCTET STRING (SIZE (1..91))
-- Refers to geographical Information defined in 3GPP TS 23.032.
-- This is composed of 1 or more octets with an internal structure according to
-- 3GPP TS 23.032
-- Octet 1: Type of shape, all the shapes defined in 3GPP TS 23.032 are allowed:
-- Octets 2 to n (where n is the total number of octets necessary to encode the shape
-- according to 3GPP TS 23.032) are used to encode the shape itself in accordance with the
-- encoding defined in 3GPP TS 23.032
--
-- An Add-GeographicalInformation parameter, whether valid or invalid, received
-- together with a valid Ext-GeographicalInformation parameter in the same message
-- shall be discarded.
--
-- An Add-GeographicalInformation parameter containing any shape not defined in
-- 3GPP TS 23.032 or an incorrect number of octets or coding according to
-- 3GPP TS 23.032 shall be treated as invalid data by a receiver if not received
-- together with a valid Ext-GeographicalInformation parameter in the same message.


TargetMS ::= CHOICE {
            imsi         [0] IMPLICIT IMSI, 
            msisdn       [1] IMPLICIT ISDN-AddressString}

--sendRoutingInfoForLCS OPERATION
--   ARGUMENT
RoutingInfoForLCS-Arg ::= SEQUENCE {
         mlcNumber            [0] IMPLICIT ISDN-AddressString, 
         targetMS             [1] IMPLICIT SubscriberIdentity, 
         extensionContainer   [2] IMPLICIT ExtensionContainer OPTIONAL
         }
--   RESULT

RoutingInfoForLCS-Res ::= SEQUENCE {
	targetMS					[0] SubscriberIdentity,
	lcsLocationInfo				[1] LCSLocationInfo,
	extensionContainer			[2] ExtensionContainer OPTIONAL,
	v-gmlc-Address				[3] GSN-Address OPTIONAL,
	h-gmlc-Address				[4] GSN-Address OPTIONAL,
	ppr-Address					[5] GSN-Address OPTIONAL,
	additional-v-gmlc-Address	[6] GSN-Address OPTIONAL }
--   ERRORS {
-- systemFailure   localValue : 34, 
-- dataMissing   localValue : 35, 
-- unexpectedDataValue   localValue : 36, 
-- facilityNotSupported   localValue : 21, 
-- unknownSubscriber   localValue : 1, 
-- absentSubscriber   localValue : 27, 
-- unauthorizedRequestingNetwork   localValue : 52}
-- ::= localValue : 85

LCSLocationInfo ::= SEQUENCE {
	networkNode-Number				ISDN-AddressString,
-- NetworkNode-number can be either msc-number or sgsn-number
	lmsi							[0] IMPLICIT LMSI OPTIONAL,
	extensionContainer				[1] IMPLICIT ExtensionContainer OPTIONAL,
	gprsNodeIndicator				[2] IMPLICIT NULL OPTIONAL,
-- gprsNodeIndicator is set only if the SGSN number is sent as the Network Node Number
	additional-Number				[3] IMPLICIT Additional-Number OPTIONAL,
	supportedLCS-CapabilitySets		[4] IMPLICIT SupportedLCS-CapabilitySets OPTIONAL,
	additional-LCS-CapabilitySets	[5] IMPLICIT SupportedLCS-CapabilitySets OPTIONAL
	}

--subscriberLocationReport OPERATION
--   ARGUMENT

SubscriberLocationReport-Arg ::= SEQUENCE {
	lcs-Event						LCS-Event,
	lcs-ClientID					LCS-ClientID,
	lcsLocationInfo					LCSLocationInfo,
	msisdn							[0] IMPLICIT ISDN-AddressString OPTIONAL,
	imsi							[1] IMPLICIT IMSI OPTIONAL,
	imei							[2] IMPLICIT IMEI OPTIONAL,
	na-ESRD							[3] IMPLICIT ISDN-AddressString OPTIONAL,
	na-ESRK							[4] IMPLICIT ISDN-AddressString OPTIONAL,
	locationEstimate				[5] IMPLICIT Ext-GeographicalInformation OPTIONAL,
	ageOfLocationEstimate			[6] IMPLICIT AgeOfLocationInformation OPTIONAL,
	slr-ArgExtensionContainer		[7] IMPLICIT SLR-ArgExtensionContainer OPTIONAL,
	add-LocationEstimate			[8] IMPLICIT Add-GeographicalInformation OPTIONAL,
	deferredmt-lrData				[9] IMPLICIT Deferredmt-lrData OPTIONAL,
	lcs-ReferenceNumber				[10] IMPLICIT LCS-ReferenceNumber OPTIONAL,
	geranPositioningData			[11] IMPLICIT PositioningDataInformation OPTIONAL,
	utranPositioningData			[12] IMPLICIT UtranPositioningDataInfo OPTIONAL,
	cellIdOrSai						[13] IMPLICIT CellGlobalIdOrServiceAreaIdOrLAI OPTIONAL,
	h-gmlc-Address					[14] IMPLICIT GSN-Address OPTIONAL,
	lcsServiceTypeID				[15] IMPLICIT LCSServiceTypeID OPTIONAL,
	sai-Present						[17] IMPLICIT NULL OPTIONAL,
	pseudonymIndicator				[18] IMPLICIT NULL OPTIONAL }
	
-- one of msisdn or imsi is mandatory
-- a location estimate that is valid for the locationEstimate parameter should
-- be transferred in this parameter in preference to the add-LocationEstimate.
-- the deferredmt-lrData parameter shall be included if and only if the lcs-Event
-- indicates a deferredmt-lrResponse.
-- if the lcs-Event indicates a deferredmt-lrResponse then the locationEstimate
-- and the add-locationEstimate parameters shall not be sent if the
-- supportedGADShapes parameter had been received in ProvideSubscriberLocation-Arg
-- and the shape encoded in locationEstimate or add-LocationEstimate was not marked
-- as supported in supportedGADShapes. In such a case terminationCause
-- in deferredmt-lrData shall be present with value
-- shapeOfLocationEstimateNotSupported.
-- If a lcs event indicates deferred mt-lr response, the lcs-Reference number shall be
-- included.
-- sai-Present indicates that the cellIdOrSai parameter contains a Service Area Identity.

Deferredmt-lrData ::= SEQUENCE {
	deferredLocationEventType	DeferredLocationEventType,
	terminationCause			[0] IMPLICIT TerminationCause OPTIONAL,
	lcsLocationInfo				[1] IMPLICIT LCSLocationInfo OPTIONAL
  }
-- lcsLocationInfo may be included only if a terminationCause is present
-- indicating mt-lrRestart.

LCS-Event ::= ENUMERATED {
	emergencyCallOrigination (0),
	emergencyCallRelease (1),
	mo-lr (2),
	deferredmt-lrResponse (3) }
-- exception handling:
-- a SubscriberLocationReport-Arg containing an unrecognized LCS-Event
-- shall be rejected by a receiver with a return error cause of unexpected data value

TerminationCause ::= ENUMERATED {
	normal (0),
	errorundefined (1),
	internalTimeout (2),
	congestion (3),
	mt-lrRestart (4),
	privacyViolation (5),
	shapeOfLocationEstimateNotSupported (6) }
-- mt-lrRestart shall be used to trigger the GMLC to restart the location procedure,
-- either because the sending node knows that the terminal has moved under coverage
-- of another MSC or SGSN (e.g. Send Identification received), or because the subscriber
-- has been deregistered due to a Cancel Location received from HLR.
--
-- exception handling
-- an unrecognized value shall be treated the same as value 1 (errorundefined)




--   RESULT
SubscriberLocationReport-Res ::= SEQUENCE {
	extensionContainer ExtensionContainer OPTIONAL,
	na-ESRK [0] IMPLICIT ISDN-AddressString OPTIONAL,
	na-ESRD [1] IMPLICIT ISDN-AddressString OPTIONAL }
	
-- na-ESRK and na-ESRD are mutually exclusive
--
-- exception handling
-- receipt of both na-ESRK and na-ESRD shall be treated the same as a return error
--   ERRORS {
-- systemFailure   localValue : 34, 
-- dataMissing   localValue : 35, 
-- unexpectedDataValue   localValue : 36, 
-- resourceLimitation   localValue : 51, 
-- unknownSubscriber   localValue : 1, 
-- unauthorizedRequestingNetwork   localValue : 52, 
-- unknownOrUnreachableLCSClient   localValue : 58}
-- ::= localValue : 86


SecureTransportArg ::= SEQUENCE {
	securityHeader		SecurityHeader,
	protectedPayload	ProtectedPayload OPTIONAL
}
-- The protectedPayload carries the result of applying the security function
-- defined in 3GPP TS 33.200 to the encoding of the argument of the securely
-- transported operation

SecureTransportRes ::= SEQUENCE {
	securityHeader		SecurityHeader,
	protectedPayload	ProtectedPayload OPTIONAL
}
-- The protectedPayload carries the result of applying the security function
-- defined in 3GPP TS 33.200 to the encoding of the result of the securely
-- transported operation

SecurityHeader ::= SEQUENCE {
	securityParametersIndex			SecurityParametersIndex,
	originalComponentIdentifier		OriginalComponentIdentifier,
	initialisationVector			InitialisationVector OPTIONAL
  }

ProtectedPayload ::= OCTET STRING(SIZE(1.. 3438))
-- In protection mode 0 (noProtection) the ProtectedPayload carries the transfer
-- syntax value of the component parameter identified by the
-- originalComponentIdentifier.
-- In protection mode 1 (integrityAuthenticity) the protectedPayload carries
-- the transfer syntax value of the component
-- parameter identified by the originalComponentIdentifier, followed by
-- the 32 bit integrity check value.
-- The integrity check value is the result of applying the hash algorithm
-- to the concatenation of the transfer syntax value of the SecurityHeader,
-- and the transfer syntax value of the component parameter.
-- In protection mode 2 (confidentialityIntegrityAuthenticity) the protected
-- payload carries the encrypted transfer syntax
-- value of the component parameter identified by the
-- originalComponentIdentifier, followed by the 32 bit integrity check value.
-- The integrity check value is the result of applying the hash algorithm
-- to the concatenation of the transfer syntax value of the SecurityHeader,
-- and the encrypted transfer syntax value of the component parameter.
-- See 33.200.
-- The length of the protectedPayload is adjusted according to the capabilities of
-- the lower protocol layers

SecurityParametersIndex ::= OCTET STRING (SIZE(4))

InitialisationVector ::= OCTET STRING (SIZE(14))
-- the internal structure is defined as follows:
-- Octets 1 to 4 : TVP. The TVP is a 32 bit time stamp. Its value is binary coded
-- and indicates the number of intervals of 100 milliseconds
-- elapsed since 1st January 2002, 0:00:00 UTC
-- Octets 5 to 10: NE-Id. The NE-Id uniquely identifies the sending network entity
-- within the PLMN. It is the entity's E.164 number without CC and
-- NDC. It is TBCD-coded, padded with zeros.
-- Octets 11 to 14: PROP. This 32 bit value is used to make the
-- InitialisationVector unique within the same TVP period.
-- The content is not standardized.

OriginalComponentIdentifier ::= CHOICE {
	operationCode	[0] IMPLICIT OperationCode,
	errorCode		[1] IMPLICIT ErrorCode,
	userInfo		[2] IMPLICIT NULL}

OperationCode ::= CHOICE {
	localValue INTEGER,
	globalValue OBJECT IDENTIFIER}

ErrorCode ::= CHOICE {
	localValue INTEGER,
	globalValue OBJECT IDENTIFIER}

GlobalCellId ::= OCTET STRING (SIZE (5..7))
-- Refers to Cell Global Identification defined in TS 3GPP TS 23.003 [17].
-- The internal structure is defined as follows:
-- octet 1 bits 4321 Mobile Country Code 1st digit
-- bits 8765 Mobile Country Code 2nd digit
-- octet 2 bits 4321 Mobile Country Code 3rd digit
-- bits 8765 Mobile Network Code 3rd digit
-- or filler (1111) for 2 digit MNCs
-- octet 3 bits 4321 Mobile Network Code 1st digit
-- bits 8765 Mobile Network Code 2nd digit
-- octets 4 and 5 Location Area Code according to TS 3GPP TS 24.008[35]
-- octets 6 and 7 Cell Identity (CI) according to TS 3GPP TS 24.008[35]

NetworkResource ::= ENUMERATED {
  plmn              ( 0 ), 
  hlr               ( 1 ), 
  vlr               ( 2 ), 
  pvlr              ( 3 ), 
  controllingMSC    ( 4 ), 
  vmsc              ( 5 ), 
  eir               ( 6 ), 
  rss               ( 7 ) }

--systemFailure ERROR
--   PARAMETER
SystemFailureParam ::= CHOICE {
         networkResource                  NetworkResource, 
         extensibleSystemFailureParam     SEQUENCE {
            networkResource      NetworkResource OPTIONAL, 
            extensionContainer   ExtensionContainer OPTIONAL
            }}
-- ::= localValue : 34

--dataMissing ERROR
--  PARAMETER
DataMissingParam ::= SEQUENCE {
         extensionContainer   ExtensionContainer OPTIONAL
         }
-- ::= localValue : 35

--unexpectedDataValue ERROR
--   PARAMETER
UnexpectedDataParam ::= SEQUENCE {
         extensionContainer   ExtensionContainer OPTIONAL
         }
-- ::= localValue : 36

--facilityNotSupported ERROR
--   PARAMETER
FacilityNotSupParam ::= SEQUENCE {
         extensionContainer   ExtensionContainer OPTIONAL
         }
-- ::= localValue : 21

OR-NotAllowedParam ::= SEQUENCE {
	extensionContainer ExtensionContainer OPTIONAL
  }

--incompatibleTerminal ERROR
--   PARAMETER
IncompatibleTerminalParam ::= SEQUENCE {
         extensionContainer   ExtensionContainer OPTIONAL
         }
-- ::= localValue : 28

--resourceLimitation ERROR
--   PARAMETER
ResourceLimitationParam ::= SEQUENCE {
         extensionContainer   ExtensionContainer OPTIONAL
         }
-- ::= localValue : 51

--unknownSubscriber ERROR
--   PARAMETER
UnknownSubscriberParam ::= SEQUENCE {
         extensionContainer            ExtensionContainer OPTIONAL, 
         unknownSubscriberDiagnostic   ENUMERATED {
            imsiUnknown                ( 0 ), 
            gprsSubscriptionUnknown    ( 1 )
            } OPTIONAL}
-- ::= localValue : 1

--numberChanged ERROR
--  PARAMETER
NumberChangedParam ::= SEQUENCE {
         extensionContainer   ExtensionContainer OPTIONAL
         }
-- ::= localValue : 44

--unknownMSC ERROR
-- ::= localValue : 3

--unidentifiedSubscriber ERROR
--   PARAMETER
UnidentifiedSubParam ::= SEQUENCE {
         extensionContainer   ExtensionContainer OPTIONAL
         }
-- ::= localValue : 5

--unknownEquipment ERROR
-- ::= localValue : 7

--roamingNotAllowed ERROR
--   PARAMETER
RoamingNotAllowedParam ::= SEQUENCE {
         roamingNotAllowedCause   ENUMERATED {
            plmnRoamingNotAllowed        ( 0 ), 
            operatorDeterminedBarring    ( 3 ) }, 
         extensionContainer       ExtensionContainer OPTIONAL
         }
-- ::= localValue : 8

--illegalSubscriber ERROR
--   PARAMETER
IllegalSubscriberParam ::= SEQUENCE {
         extensionContainer   ExtensionContainer OPTIONAL
         }
-- ::= localValue : 9

--illegalEquipment ERROR
--   PARAMETER
IllegalEquipmentParam ::= SEQUENCE {
         extensionContainer   ExtensionContainer OPTIONAL
         }
-- ::= localValue : 12

--bearerServiceNotProvisioned ERROR
--   PARAMETER
BearerServNotProvParam ::= SEQUENCE {
         extensionContainer   ExtensionContainer OPTIONAL
         }
-- ::= localValue : 10

--teleserviceNotProvisioned ERROR
--   PARAMETER
TeleservNotProvParam ::= SEQUENCE {
         extensionContainer   ExtensionContainer OPTIONAL
         }
-- ::= localValue : 11

--noHandoverNumberAvailable ERROR
-- ::= localValue : 25

--subsequentHandoverFailure ERROR
-- ::= localValue : 26

--tracingBufferFull ERROR
--   PARAMETER
TracingBufferFullParam ::= SEQUENCE {
         extensionContainer   ExtensionContainer OPTIONAL
         }
-- ::= localValue : 40

--noRoamingNumberAvailable ERROR
--   PARAMETER
NoRoamingNbParam ::= SEQUENCE {
         extensionContainer   ExtensionContainer OPTIONAL
         }
-- ::= localValue : 39

--absentSubscriber ERROR
--   PARAMETER

AbsentSubscriberParam ::= SEQUENCE {
	extensionContainer		ExtensionContainer OPTIONAL,
	absentSubscriberReason	[0] IMPLICIT AbsentSubscriberReason OPTIONAL
	}

-- ::= localValue : 27
AbsentSubscriberReason ::= ENUMERATED {
	imsiDetach (0),
	restrictedArea (1),
	noPageResponse (2),
	purgedMS (3)
	}

-- exception handling: at reception of other values than the ones listed the
-- AbsentSubscriberReason shall be ignored.
-- The AbsentSubscriberReason: purgedMS is defined for the Super-Charger feature
-- (see TS 23.116). If this value is received in a Provide Roaming Number response
-- it shall be mapped to the AbsentSubscriberReason: imsiDetach in the Send Routeing
-- Information response

--busySubscriber ERROR
--   PARAMETER
BusySubscriberParam ::= SEQUENCE {
         extensionContainer   ExtensionContainer OPTIONAL,
         ccbs-Possible        [0] IMPLICIT NULL OPTIONAL, 
         ccbs-Busy            [1] IMPLICIT NULL OPTIONAL}
-- ::= localValue : 45

--noSubscriberReply ERROR
--   PARAMETER
NoSubscriberReplyParam ::= SEQUENCE {
         extensionContainer   ExtensionContainer OPTIONAL
         }
-- ::= localValue : 46

--forwardingViolation ERROR
--   PARAMETER
ForwardingViolationParam ::= SEQUENCE {
         extensionContainer   ExtensionContainer OPTIONAL
         }
-- ::= localValue : 14

--forwardingFailed ERROR
--   PARAMETER
ForwardingFailedParam ::= SEQUENCE {
         extensionContainer   ExtensionContainer OPTIONAL
         }
-- ::= localValue : 47

--ati-NotAllowed ERROR
--   PARAMETER
ATI-NotAllowedParam ::= SEQUENCE {
         extensionContainer   ExtensionContainer OPTIONAL
         }
-- ::= localValue : 49

ATSI-NotAllowedParam ::= SEQUENCE {
		extensionContainer ExtensionContainer OPTIONAL
		}

ATM-NotAllowedParam ::= SEQUENCE {
		extensionContainer ExtensionContainer OPTIONAL
		}

IllegalSS-OperationParam ::= SEQUENCE {
		extensionContainer ExtensionContainer OPTIONAL
		}
SS-NotAvailableParam ::= SEQUENCE {
		extensionContainer ExtensionContainer OPTIONAL
		}

SS-SubscriptionViolationParam ::= SEQUENCE {
		extensionContainer ExtensionContainer OPTIONAL
		}

InformationNotAvailableParam ::= SEQUENCE {
		extensionContainer ExtensionContainer OPTIONAL
		}

--subscriberBusyForMT-SMS ERROR
--   PARAMETER
SubBusyForMT-SMS-Param ::= SEQUENCE {
         extensionContainer        ExtensionContainer OPTIONAL,
         gprsConnectionSuspended   NULL OPTIONAL}
-- ::= localValue : 31

--callBarred ERROR
--   PARAMETER
CallBarredParam ::= CHOICE {
         callBarringCause              CallBarringCause, 
         extensibleCallBarredParam     ExtensibleCallBarredParam
			}
-- ::= localValue : 13

CallBarringCause ::= ENUMERATED {
            barringServiceActive    ( 0 ), 
            operatorBarring         ( 1 ) 
}

ExtensibleCallBarredParam ::= SEQUENCE {
	callBarringCause					CallBarringCause OPTIONAL,
	extensionContainer					ExtensionContainer OPTIONAL,
	unauthorisedMessageOriginator		[1] NULL OPTIONAL 
	}

--cug-Reject ERROR
--   PARAMETER
CUG-RejectParam ::= SEQUENCE {
	cug-RejectCause			CUG-RejectCause OPTIONAL,
	extensionContainer		ExtensionContainer OPTIONAL
	}
-- ::= localValue : 15

CUG-RejectCause ::= ENUMERATED {
	incomingCallsBarredWithinCUG					(0),
	subscriberNotMemberOfCUG						(1),
	requestedBasicServiceViolatesCUG-Constraints	(5),
	calledPartySS-InteractionViolation				(7)
	}


--or-NotAllowed ERROR
--   PARAMETER
Or-NotAllowedParam ::= SEQUENCE {
         extensionContainer   ExtensionContainer OPTIONAL
         }
-- ::= localValue : 48


--noGroupCallNumberAvailable ERROR
--   PARAMETER
NoGroupCallNbParam ::= SEQUENCE {
         extensionContainer   ExtensionContainer OPTIONAL
         }
-- ::= localValue : 50

--illegalSS-Operation ERROR
-- ::= localValue : 16

--ss-ErrorStatus ERROR
--   PARAMETER
-- Ss-Statis is also declared as OCTET STRING ( SIZE( 1..5 ) ) ???
-- SS-Status ::= OCTET STRING ( SIZE( 1 ) )
-- ::= localValue : 17

--ss-NotAvailable ERROR
-- ::= localValue : 18

--ss-SubscriptionViolation ERROR
-- ::= localValue : 19

--ss-Incompatibility ERROR
--   PARAMETER
SS-IncompatibilityCause ::= SEQUENCE {
	ss-Code			[1] IMPLICIT SS-Code OPTIONAL,
	basicService	BasicServiceCode OPTIONAL,
	ss-Status		[4] IMPLICIT SS-Status OPTIONAL
  }
--unknownAlphabet ERROR
-- ::= localValue : 71

--ussd-Busy  ERROR
-- ::= localValue : 72

--pw-RegistrationFailure ERROR
--   PARAMETER

PW-RegistrationFailureCause ::= ENUMERATED {
	undetermined (0),
	invalidFormat (1),
	newPasswordsMismatch (2)
	}
-- ::= localValue : 37

--negativePW-Check ERROR
-- ::= localValue : 38

--numberOfPW-AttemptsViolation ERROR
-- ::= localValue : 43

--shortTermDenial ERROR
--   PARAMETER
ShortTermDenialParam ::= SEQUENCE {
     }
-- ::= localValue : 29

--longTermDenial ERROR
--   PARAMETER
LongTermDenialParam ::= SEQUENCE {
    }
-- ::= localValue : 30


--sm-DeliveryFailure ERROR
--   PARAMETER
SM-EnumeratedDeliveryFailureCause ::= ENUMERATED {
	memoryCapacityExceeded (0),
	equipmentProtocolError (1),
	equipmentNotSM-Equipped (2),
	unknownServiceCentre (3),
	sc-Congestion (4),
	invalidSME-Address (5),
	subscriberNotSC-Subscriber (6)
	}

SM-DeliveryFailureCause ::= SEQUENCE {
	sm-EnumeratedDeliveryFailureCause	SM-EnumeratedDeliveryFailureCause,
	diagnosticInfo						SignalInfo OPTIONAL,
	extensionContainer					ExtensionContainer OPTIONAL
  }
-- ::= localValue : 32


--messageWaitingListFull ERROR
--   PARAMETER
MessageWaitListFullParam ::= SEQUENCE {
         extensionContainer   ExtensionContainer OPTIONAL
         }
-- ::= localValue : 33

--absentsubscriberSM ERROR
--   PARAMETER
AbsentSubscriberSM-Param ::= SEQUENCE {
	absentSubscriberDiagnosticSM			AbsentSubscriberDiagnosticSM OPTIONAL,
-- AbsentSubscriberDiagnosticSM can be either for non-GPRS
-- or for GPRS
	extensionContainer						ExtensionContainer OPTIONAL,
	additionalAbsentSubscriberDiagnosticSM	[0] IMPLICIT AbsentSubscriberDiagnosticSM OPTIONAL }
-- if received, additionalAbsentSubscriberDiagnosticSM
-- is for GPRS and absentSubscriberDiagnosticSM is
-- for non-GPRS
-- ::= localValue : 6

AbsentSubscriberDiagnosticSM ::= INTEGER (0..255)
-- AbsentSubscriberDiagnosticSM values are defined in 3GPP TS 23.040


--unauthorizedRequestingNetwork ERROR
--   PARAMETER
UnauthorizedRequestingNetwork-Param ::= SEQUENCE {
         extensionContainer   ExtensionContainer OPTIONAL
         }
-- ::= localValue : 52

--unauthorizedLCSClient ERROR
--   PARAMETER
UnauthorizedLCSClient-Param ::= SEQUENCE {
         unauthorizedLCSClient-Diagnostic   [0] IMPLICIT ENUMERATED {
            noAdditionalInformation                    ( 0 ), 
            clientNotInMSPrivacyExceptionList          ( 1 ), 
            callToClientNotSetup                       ( 2 ), 
            privacyOverrideNotApplicable               ( 3 ), 
            disallowedByLocalRegulatoryRequirements    ( 4 ) 
            } OPTIONAL, 
         extensionContainer                 [1] IMPLICIT ExtensionContainer OPTIONAL
         }
-- ::= localValue : 53

--positionMethodFailure ERROR
--   PARAMETER
PositionMethodFailure-Param ::= SEQUENCE {
	positionMethodFailure-Diagnostic		[0] IMPLICIT PositionMethodFailure-Diagnostic OPTIONAL,
	extensionContainer						[1] IMPLICIT ExtensionContainer OPTIONAL
	}


PositionMethodFailure-Diagnostic ::= ENUMERATED {
	congestion (0),
	insufficientResources (1),
	insufficientMeasurementData (2),
	inconsistentMeasurementData (3),
	locationProcedureNotCompleted (4),
	locationProcedureNotSupportedByTargetMS (5),
	qoSNotAttainable (6),
	positionMethodNotAvailableInNetwork (7),
	positionMethodNotAvailableInLocationArea (8)
	}
-- exception handling:
-- any unrecognized value shall be ignored
-- ::= localValue : 54

--unknownOrUnreachableLCSClient ERROR
--   PARAMETER
UnknownOrUnreachableLCSClient-Param ::= SEQUENCE {
         extensionContainer   ExtensionContainer OPTIONAL
         }
-- ::= localValue : 58

MM-EventNotSupported-Param ::= SEQUENCE {
	extensionContainer ExtensionContainer OPTIONAL
	}

TargetCellOutsideGCA-Param ::= SEQUENCE {
	extensionContainer ExtensionContainer OPTIONAL
	}

SecureTransportErrorParam ::= SEQUENCE {
	securityHeader		SecurityHeader,
	protectedPayload	ProtectedPayload OPTIONAL
}
-- The protectedPayload carries the result of applying the security function
-- defined in 3GPP TS 33.200 to the encoding of the securely transported error
-- parameter

ExtensionContainer ::=    SEQUENCE {
   privateExtensionList [0] IMPLICIT PrivateExtensionList OPTIONAL, 
   pcsExtensions     [1] IMPLICIT PcsExtensions OPTIONAL 
   }

-- Private extensions
accessType-id	OBJECT IDENTIFIER ::=
		{1 3 12 2 1107 3 66 1 1}
	
	--iso (1)
	--identified-organization (3)
	--ecma (12)
	--member-company (2)
	--siemens-units (1107)
	--oen (3)
	--mn (66)
	--proprietary-extensions (1)
	--accessType (1)

accessTypeNotAllowed-id	OBJECT IDENTIFIER ::=
		{1 3 12 2 1107 3 66 1 2}
	
	--iso (1)
	--identified-organization (3)
	--ecma (12)
	--member-company (2)
	--siemens-units (1107)
	--oen (3)
	--mn (66)
	--proprietary-extensions (1)
	--accessTypeNotAllowed (2)

--accessType		MAP-EXTENSION ::= {
--		&ExtensionType	AccessType,
--		&extensionId	accessType-id}

AccessTypePriv	::=	SEQUENCE {
		access	Access,
		version	Version
    }

Access	::=		ENUMERATED {
		gsm		(1),
		geran	(2),
		utran	(3)
    }

Version ::= INTEGER (1..20)


END
